module cisco-xe-openconfig-isis-policy-deviation {
  namespace "http://cisco.com/ns/yang/cisco-xe-openconfig-isis-policy-deviation";
  prefix oc-isis-pol-devs;

  import openconfig-routing-policy {
    prefix oc-rpol;
  }
  import openconfig-isis-policy {
    prefix oc-isis-pol;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-isis-policy module.
     Copyright (c) 2020 by Cisco Systems, Inc.
     All rights reserved.";

  revision 2020-07-30 {
    description
      "Initial Revision";
    reference
      "RFC 6020: YANG - A Data Modeling Language for the
       Network Configuration Protocol (NETCONF)";
  }

  deviation "/oc-rpol:routing-policy/oc-rpol:policy-definitions/oc-rpol:policy-definition/oc-rpol:statements/oc-rpol:statement/oc-rpol:actions/oc-rpol:igp-actions/oc-isis-pol:isis-actions" {
    deviate not-supported;
    description
      "Not supported in IOS-XE";
  }

  deviation "/oc-rpol:routing-policy/oc-rpol:policy-definitions/oc-rpol:policy-definition/oc-rpol:statements/oc-rpol:statement/oc-rpol:conditions/oc-rpol:igp-conditions/oc-isis-pol:isis-conditions" {
    deviate not-supported;
    description
      "Not supported in IOS-XE";
  }
}
