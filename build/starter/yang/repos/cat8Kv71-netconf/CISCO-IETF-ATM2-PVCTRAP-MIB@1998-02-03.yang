/*
 * Generated by confdc --mib2yang-std
 * Source: mgmt/dmi/model/mib/src/CISCO-IETF-ATM2-PVCTRAP-MIB.mib
 */
/*
 * This YANG module has been generated by smidump 0.5.0:
 *
 *      smidump -f yang CISCO-IETF-ATM2-PVCTRAP-MIB
 *
 * Do not edit. Edit the source file instead!
 */

module CISCO-IETF-ATM2-PVCTRAP-MIB {

  namespace "urn:ietf:params:xml:ns:yang:smiv2:CISCO-IETF-ATM2-PVCTRAP-MIB";
  prefix CISCO-IETF-ATM2-PVCTRAP-MIB;

  import ATM-MIB {
    prefix "atm-mib";
  }

  import IF-MIB {
    prefix "if-mib";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-atm@cisco.com";

  description
   "This MIB Module is a supplement to the
    ATM-MIB.";

  revision 1998-02-03 {
    description
     "[Revision added by libsmi due to a LAST-UPDATED clause.]";
  }


  container CISCO-IETF-ATM2-PVCTRAP-MIB {
    config false;

    container atmCurrentlyFailingPVclTable {
      description
       "A table indicating all VCLs for which there is an
        active row in the atmVclTable having an atmVclConnKind
        value of `pvc' and an atmVclOperStatus with a value
        other than `up'.";
      smiv2:oid "1.3.6.1.4.1.9.10.29.1.21";

      list atmCurrentlyFailingPVclEntry {
        key "ifIndex atmVclVpi atmVclVci";
        description
         "Each entry in this table represents a VCL for which
          the atmVclRowStatus is `active', the atmVclConnKind is
          `pvc', and the atmVclOperStatus is other than `up'.";
        smiv2:oid "1.3.6.1.4.1.9.10.29.1.21.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf atmCurrentlyFailingPVclTimeStamp {
          type yang:timestamp;
          description
           "The time at which this PVCL began to fail.";
          smiv2:max-access "read-only";
          smiv2:oid "1.3.6.1.4.1.9.10.29.1.21.1.1";
        }

        leaf atmPreviouslyFailedPVclTimeStamp {
          type yang:timestamp;
          description
           "The time at which this PVCL began to fail
            during the PVC Notification interval.";
          smiv2:max-access "read-only";
          smiv2:oid "1.3.6.1.4.1.9.10.29.1.21.1.2";
        }
      }
    }
  }

  smiv2:alias "atmInterfaceExtTable" {
    description
     "This table contains ATM interface monitoring
      information not defined in the
      atmInterfaceConfTable from the ATM-MIB.";
    smiv2:oid "1.3.6.1.4.1.9.10.29.1.14";
  }

  smiv2:alias "atmInterfaceExtEntry" {
    description
     "An entry extends the atmInterfaceConfEntry
      defined in ATM MIB.  Each entry corresponds
      to an ATM interface.";
    smiv2:oid "1.3.6.1.4.1.9.10.29.1.14.1";
  }

  augment "/atm-mib:ATM-MIB/atm-mib:atmInterfaceConfTable/atm-mib:atmInterfaceConfEntry" {
    description
     "An entry extends the atmInterfaceConfEntry
      defined in ATM MIB.  Each entry corresponds
      to an ATM interface.";
    smiv2:oid "1.3.6.1.4.1.9.10.29.1.14.1";

    leaf atmIntfPvcFailures {
      type yang:counter32;
      description
       "The number of times the operational status of a PVCL
        on this interface has gone down.";
      smiv2:max-access "read-only";
      smiv2:oid "1.3.6.1.4.1.9.10.29.1.14.1.20";
    }

    leaf atmIntfCurrentlyFailingPVcls {
      type yang:gauge32;
      description
       "The current number of VCLs on this interface for which
        there is an active row in the atmVclTable having an
        atmVclConnKind value of `pvc' and an atmVclOperStatus
        with a value other than `up'.";
      smiv2:max-access "read-only";
      smiv2:oid "1.3.6.1.4.1.9.10.29.1.14.1.22";
    }

    leaf atmIntfPvcFailuresTrapEnable {
      type boolean;
      description
       "Allows the generation of traps in response to PVCL
        failures on this interface.";
      smiv2:defval "false";
      smiv2:max-access "read-write";
      smiv2:oid "1.3.6.1.4.1.9.10.29.1.14.1.23";
    }

    leaf atmIntfPvcNotificationInterval {
      type int32 {
        range "1..3600";
      }
      units "seconds";
      description
       "The minimum interval between the sending of
        cIntfPvcFailuresTrap notifications for this
        interface.";
      smiv2:defval "30";
      smiv2:max-access "read-write";
      smiv2:oid "1.3.6.1.4.1.9.10.29.1.14.1.24";
    }

    leaf atmPreviouslyFailedPVclInterval {
      type int32 {
        range "0..3600";
      }
      units "seconds";
      description
       "The interval for storing the failed
        time in atmPreviouslyFailedPVclTimeStamp";
      smiv2:defval "0";
      smiv2:max-access "read-write";
      smiv2:oid "1.3.6.1.4.1.9.10.29.1.14.1.25";
    }
  }

  notification atmIntfPvcFailuresTrap {
    description
     "A notification indicating that one or more
      PVCLs on this interface has failed since the last
      cIntfPvcFailuresTrap was sent.  If this trap has not been
      sent for the last cIntfPvcNotificationInterval, then
      it will be sent on the next increment of
      cIntfPvcFailures.";
    smiv2:oid "1.3.6.1.4.1.9.10.29.2.1.0.1";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf atmIntfPvcFailures {
        type leafref {
          path "/atm-mib:ATM-MIB/atm-mib:atmInterfaceConfTable/atm-mib:atmInterfaceConfEntry/CISCO-IETF-ATM2-PVCTRAP-MIB:atmIntfPvcFailures";
        }
      }
    }

    container object-3 {

      leaf ifIndex {
        type leafref {
          path "/if-mib:IF-MIB/if-mib:ifTable/if-mib:ifEntry/if-mib:ifIndex";
        }
      }

      leaf atmIntfCurrentlyFailingPVcls {
        type leafref {
          path "/atm-mib:ATM-MIB/atm-mib:atmInterfaceConfTable/atm-mib:atmInterfaceConfEntry/CISCO-IETF-ATM2-PVCTRAP-MIB:atmIntfCurrentlyFailingPVcls";
        }
      }
    }
  }

  smiv2:alias "ciscoIetfAtm2PvctrapMIB" {
    smiv2:oid "1.3.6.1.4.1.9.10.29";
  }

  smiv2:alias "atm2MIBObjects" {
    smiv2:oid "1.3.6.1.4.1.9.10.29.1";
  }

  smiv2:alias "atm2MIBTraps" {
    smiv2:oid "1.3.6.1.4.1.9.10.29.2";
  }

  smiv2:alias "atmPvcTraps" {
    smiv2:oid "1.3.6.1.4.1.9.10.29.2.1";
  }

  smiv2:alias "atmPvcTrapsPrefix" {
    smiv2:oid "1.3.6.1.4.1.9.10.29.2.1.0";
  }

  smiv2:alias "atm2MIBConformance" {
    smiv2:oid "1.3.6.1.4.1.9.10.29.3";
  }

  smiv2:alias "atm2MIBGroups" {
    smiv2:oid "1.3.6.1.4.1.9.10.29.3.1";
  }

  smiv2:alias "atm2MIBCompliances" {
    smiv2:oid "1.3.6.1.4.1.9.10.29.3.2";
  }

}
