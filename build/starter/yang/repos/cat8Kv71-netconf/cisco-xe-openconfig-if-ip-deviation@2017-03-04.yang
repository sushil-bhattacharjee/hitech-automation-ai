module cisco-xe-openconfig-if-ip-deviation {
  namespace "http://openconfig.net/yang/cisco-xe-openconfig-if-ip-deviation";
  prefix oc-ifip-devs;

  import openconfig-interfaces {
    prefix oc-if;
  }
  import openconfig-if-ip {
    prefix oc-ip;
  }
  import openconfig-vlan {
    prefix oc-vlan;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-if-ip module.";

  revision 2017-03-04 {
    description
      "Remove ipv6 default enabled not compatibile with switches";
    reference
      "RFC 6020: YANG - A Data Modeling Language for the
       Network Configuration Protocol (NETCONF)";
  }

  deviation "/oc-if:interfaces/oc-if:interface/oc-vlan:routed-vlan/oc-ip:ipv6/oc-ip:config/oc-ip:enabled" {
    deviate delete {
      default "true";
    }
    description
      "Enabling ipv6 by default incompatible with switchport interfaces";
  }

  deviation "/oc-if:interfaces/oc-if:interface/oc-vlan:routed-vlan/oc-ip:ipv6/oc-ip:neighbors/oc-ip:neighbor/oc-ip:config/oc-ip:link-layer-address" {
    deviate replace {
      type string {
        pattern '([0-9a-fA-F]{2}(:[0-9a-fA-F]{2})*)?';
      }
      mandatory true;
    }
    description
      "The link-layer v6 address of the neighbor node for routed-vlan.";
  }

  deviation "/oc-if:interfaces/oc-if:interface/oc-vlan:routed-vlan/oc-ip:ipv4/oc-ip:neighbors/oc-ip:neighbor/oc-ip:config/oc-ip:link-layer-address" {
    deviate replace {
      type string {
        pattern '([0-9a-fA-F]{2}(:[0-9a-fA-F]{2})*)?';
      }
      mandatory true;
    }
    description
      "The link-layer v4 address of the neighbor node for routed-vlan.";
  }

  deviation "/oc-if:interfaces/oc-if:interface/oc-if:subinterfaces/oc-if:subinterface/oc-ip:ipv4/oc-ip:neighbors/oc-ip:neighbor/oc-ip:config/oc-ip:link-layer-address" {
    deviate replace {
      type string {
        pattern '([0-9a-fA-F]{2}(:[0-9a-fA-F]{2})*)?';
      }
      mandatory true;
    }
    description
      "The link-layer v4 address of the neighbor node.";
  }

  deviation "/oc-if:interfaces/oc-if:interface/oc-if:subinterfaces/oc-if:subinterface/oc-ip:ipv6/oc-ip:neighbors/oc-ip:neighbor/oc-ip:config/oc-ip:link-layer-address" {
    deviate replace {
      type string {
        pattern '([0-9a-fA-F]{2}(:[0-9a-fA-F]{2})*)?';
      }
      mandatory true;
    }
    description
      "The link-layer v6 address of the neighbor node.";
  }
}
