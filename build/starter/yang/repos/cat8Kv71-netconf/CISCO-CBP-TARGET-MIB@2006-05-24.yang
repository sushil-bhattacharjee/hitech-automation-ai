/*
 * Generated by confdc --mib2yang-std
 * Source: mgmt/dmi/model/mib/src/CISCO-CBP-TARGET-MIB.mib
 */
/*
 * This YANG module has been generated by smidump 0.5.0:
 *
 *      smidump -f yang CISCO-CBP-TARGET-MIB
 *
 * Do not edit. Edit the source file instead!
 */

module CISCO-CBP-TARGET-MIB {

  namespace "urn:ietf:params:xml:ns:yang:smiv2:CISCO-CBP-TARGET-MIB";
  prefix CISCO-CBP-TARGET-MIB;

  import CISCO-CBP-TARGET-TC-MIB {
    prefix "cisco-cbp";
  }

  import SNMPv2-TC {
    prefix "snmpv2-tc";
  }

  import ietf-yang-smiv2 {
    prefix "smiv2";
  }

  import ietf-yang-types {
    prefix "yang";
  }

  organization
   "Cisco Systems, Inc.";

  contact
   "          Cisco Systems
    Customer Service
    
    Postal: 170 W. Tasman Drive
    San Jose, CA 95134-1706
    USA
    
    Tel: +1 800 553-NETS
    
    E-mail: cs-c3pl@cisco.com, cs-qos@cisco.com";

  description
   "This MIB module defines the managed objects for
    representing targets which have class-based policy  
    mappings.  A target can be any logical interface 
    to which a class-based policy is able to be associated.";

  revision 2006-05-24 {
    description
     "Initial version.";
  }


  container CISCO-CBP-TARGET-MIB {
    config false;

    container ccbptTargetAttachCfg {
      smiv2:oid "1.3.6.1.4.1.9.9.533.1.1";

      leaf ccbptPolicyIdNext {
        type cisco-cbp:CcbptPolicyIdentifierOrZero;
        description
         "This object indicates the next available value of 
          ccbptPolicyId that can be used to create a new conceptual
          row in the ccbptTargetTable.  If no available identifier
          exists, then this object will have the value '0'.";
        smiv2:max-access "read-only";
        smiv2:oid "1.3.6.1.4.1.9.9.533.1.1.1";
      }

      leaf ccbptTargetTableLastChange {
        type yang:timestamp;
        description
         "The value of sysUpTime at the time of the last
          change to an entry in the ccbptTargetTable.";
        smiv2:max-access "read-only";
        smiv2:oid "1.3.6.1.4.1.9.9.533.1.1.3";
      }
    }

    container ccbptTargetTable {
      description
       "This table describes the class-based policy attachments to
        to specific targets.";
      smiv2:oid "1.3.6.1.4.1.9.9.533.1.1.2";

      list ccbptTargetEntry {
        key "ccbptTargetType ccbptTargetId ccbptTargetDir ccbptPolicySourceType ccbptPolicyId";
        description
         "Each entry describes a class-based policy attachment to a 
          particular target. 
           
          The ccbptTargetType uniquely identifies the type of target
          in the attachment.  Additionally, the ccbptTargetId uniquely
          identifies the target in attachment and is of the format
          indicated by the ccbptTargetType.  The ccbptTargetDir 
          identifies the direction, relative to the ccbptTargetId, 
          to which the policy is attached.  The ccbptPolicySourceType
          identifies the source-type of the policy attached.  The 
          ccbptPolicyId uniquely identifies the policy within the scope
          of ccbptTargetType, ccbptTargetId, ccbptTargetDir, and 
          ccbptPolicySourceType.
          
          A class-based policy attachment to a target can be created 
          through other network management interfaces (e.g., the local
          console), in which case the SNMP entity will automatically 
          create an entry in this table.
          
          A class-based policy attachment to a target can be destroyed
          through other network management interfaces, in which case
          the SNMP entity will automatically destroy the corresponding
          entry in this table.
          
          A class-based policy attachment to a target can be created,
          destroyed, and modified through the SNMP using 
          ccbptTargetStatus using the semantics described by the 
          RowStatus Textual Convention.  However, when creating a new
          class-based policy attachment to a target, the value of
          ccbptPolicyIdNext should be used to identify the new policy
          within the scope of the target type, identifier, direction,
          and policy-source type.";
        smiv2:oid "1.3.6.1.4.1.9.9.533.1.1.2.1";

        leaf ccbptTargetType {
          type cisco-cbp:CcbptTargetType;
          description
           "The type of target for this class-based policy attachment.
            This object identifies the format of the ccbptTargetId for
            this entry.";
          smiv2:max-access "not-accessible";
          smiv2:oid "1.3.6.1.4.1.9.9.533.1.1.2.1.1";
        }

        leaf ccbptTargetId {
          type cisco-cbp:CcbptTargetId;
          description
           "The target identifier for this class-based policy attachment.
            For decoding the ccbptTargetId refer to the ccbptTargetType
            object and the CcbptTargetType description.";
          smiv2:max-access "not-accessible";
          smiv2:oid "1.3.6.1.4.1.9.9.533.1.1.2.1.2";
        }

        leaf ccbptTargetDir {
          type cisco-cbp:CcbptTargetDirection;
          description
           "The direction relative to the ccbptTargetId for this class
            based policy attachment.  ";
          smiv2:max-access "not-accessible";
          smiv2:oid "1.3.6.1.4.1.9.9.533.1.1.2.1.3";
        }

        leaf ccbptPolicySourceType {
          type cisco-cbp:CcbptPolicySourceType;
          description
           "The source-type of the class-based policy for this target.
            The source-type refers to the source of the class-based
            policy definition.  The intent of this object is to allow
            implementations to distinguish between different MIBs
            defining policy-maps. ";
          smiv2:max-access "not-accessible";
          smiv2:oid "1.3.6.1.4.1.9.9.533.1.1.2.1.4";
        }

        leaf ccbptPolicyId {
          type cisco-cbp:CcbptPolicyIdentifier;
          description
           "Unique identifier of this class-based policy instance.";
          smiv2:max-access "not-accessible";
          smiv2:oid "1.3.6.1.4.1.9.9.533.1.1.2.1.5";
        }

        leaf ccbptTargetStatus {
          type snmpv2-tc:RowStatus;
          description
           "The status of the policy attachment to this target.  The
            value for the corresponding instance of each of the 
            following objects must be valid before the attachment 
            can be activated:
                -ccbptTargetStorageType
                -ccbptPolicyMap
            
            Observe that no corresponding instance of any object in 
            this table can be modified when the value of this object is
            'active'.";
          smiv2:max-access "read-write";
          smiv2:oid "1.3.6.1.4.1.9.9.533.1.1.2.1.6";
        }

        leaf ccbptTargetStorageType {
          type snmpv2-tc:StorageType;
          description
           "This object indicates how the device stores the data 
            contained by the conceptual row.
            
            If an instance of this object has the value 'permanent',
            then this MIB definition does not require the SNMP entity
            to allow the instance of any object in the corresponding
            conceptual row to be writable through the SNMP.";
          smiv2:max-access "read-write";
          smiv2:oid "1.3.6.1.4.1.9.9.533.1.1.2.1.7";
        }

        leaf ccbptPolicyMap {
          type snmpv2-tc:RowPointer;
          description
           "Refers to the first accessible object in the policy-map
            definition table used to manage policy-map information
            for policy-maps for the corresponding ccbptPolicySourceType.
            
            Specific MIB tables are not mentioned here as the intent of
            this mapping is to allow for different implementations to 
            refer to their supported class-based policy definition table
            without requiring support of a specific MIB module.";
          smiv2:max-access "read-write";
          smiv2:oid "1.3.6.1.4.1.9.9.533.1.1.2.1.8";
        }

        leaf ccbptPolicyInstance {
          type snmpv2-tc:RowPointer;
          description
           "Refers to the first accessible object in the policy 
            instance table used to manage policy instance information 
            for policy-maps of this ccbptPolicySourceType.
            
            Specific MIB tables are not mentioned here as the intent of
            this mapping is to allow for different implementations to 
            refer to their supported class-based policy definition table
            without requiring support of a specific MIB module.";
          smiv2:max-access "read-only";
          smiv2:oid "1.3.6.1.4.1.9.9.533.1.1.2.1.9";
        }

        leaf ccbptPolicyAttachTime {
          type yang:timestamp;
          description
           "The value of sysUpTime for the last time that the corresponding
            ccbptTargetStatus instance transitioned to the 'active' state.  ";
          smiv2:max-access "read-only";
          smiv2:oid "1.3.6.1.4.1.9.9.533.1.1.2.1.10";
        }
      }
    }
  }

  smiv2:alias "ciscoCbpTargetMIB" {
    smiv2:oid "1.3.6.1.4.1.9.9.533";
  }

  smiv2:alias "ciscoCbpTargetMIBNotifs" {
    smiv2:oid "1.3.6.1.4.1.9.9.533.0";
  }

  smiv2:alias "ciscoCbpTargetMIBObjects" {
    smiv2:oid "1.3.6.1.4.1.9.9.533.1";
  }

  smiv2:alias "ccbptTargetAttachCfg" {
    smiv2:oid "1.3.6.1.4.1.9.9.533.1.1";
  }

  smiv2:alias "ciscoCbpTargetMIBConform" {
    smiv2:oid "1.3.6.1.4.1.9.9.533.2";
  }

  smiv2:alias "ciscoCbpTargetMIBCompliances" {
    smiv2:oid "1.3.6.1.4.1.9.9.533.2.1";
  }

  smiv2:alias "ciscoCbpTargetMIBMIBGroups" {
    smiv2:oid "1.3.6.1.4.1.9.9.533.2.2";
  }

}
