/*
 * Generated by confdc --mib2yang-std
 * Source: mgmt/dmi/model/mib/src/CISCO-IPMROUTE-MIB.mib
 */
/*
 * This YANG module has been generated by smidump 0.5.0:
 *
 *      smidump -f yang CISCO-IPMROUTE-MIB
 *
 * Do not edit. Edit the source file instead!
 */

module CISCO-IPMROUTE-MIB {

  namespace "urn:ietf:params:xml:ns:yang:smiv2:CISCO-IPMROUTE-MIB";
  prefix CISCO-IPMROUTE-MIB;

  import IPMROUTE-STD-MIB {
    prefix "ipmroute-std";
  }

  import SNMPv2-TC {
    prefix "snmpv2-tc";
  }

  import ietf-inet-types {
    prefix "inet";
  }

  import ietf-yang-smiv2 {
    prefix "smiv2";
  }

  import ietf-yang-types {
    prefix "yang";
  }

  organization
   "ciscoSytems";

  contact
   " cisco Systems, Inc.
    170 Tasman Drive
    San Jose, CA
    EMail: cs-ipmulticast@cisco.com";

  description
   "The MIB module for management of IP Multicast routing,
    but independent of the specific multicast routing protocol
    in use.";

  revision 2005-03-07 {
    description
     "Add 32-bit and 64-bit per interface packet counters.
      These apply to all interfaces, including Point-To-Point
      types, unlike ifInMulticastPkts etc which only apply to
      interfaces with multicast at that layer. Also fix import
      of Unsigned32.";
  }

  revision 2000-12-22 {
    description
     "Add ciscoIpMRouteNumberOfEntries. Also add 64-bit
      counters to represent information for high speed
      interfaces like OC-192. Deprecate ciscoIpMRouteBps in
      favour of the 64-bit counter ciscoIpMRouteBps2. 
      ciscoIpMouteMetric deprecated in favour of
      ciscoIpMouteMetric2 to correctly represent a 32-bit
      unsigned metric value.";
  }

  revision 2000-05-15 {
    description
     "Added MIB support for multicast heartbeat monitoring.";
  }

  revision 1999-02-08 {
    description
     "Add ciscoIpMRouteJoinFlag, ciscoIpMRouteMsdpFlag and
      ciscoIpMRouteProxyJoinFlag.";
  }

  revision 1996-10-11 {
    description
     "Obsolete ciscoIpMRouteInLimit and replaced with
      ciscoIpMRouteInLimit2.";
  }


  container CISCO-IPMROUTE-MIB {
    config false;

    container ciscoIpMRoute {
      smiv2:oid "1.3.6.1.4.1.9.10.2.1.1";

      leaf ciscoIpMRouteNumberOfEntries {
        type yang:gauge32;
        description
         "Maintains a count of the number of entries in the
          ipMRouteTable.";
        smiv2:max-access "read-only";
        smiv2:oid "1.3.6.1.4.1.9.10.2.1.1.1";
      }
    }

    container ciscoIpMRouteHeartBeatTable {
      description
       "The (conceptual) table listing sets of IP Multicast
        heartbeat parameters.  If no IP Multicast heartbeat is
        configured, this table would be empty.";
      smiv2:oid "1.3.6.1.4.1.9.10.2.1.1.4";

      list ciscoIpMRouteHeartBeatEntry {
        key "ciscoIpMRouteHeartBeatGroupAddr";
        description
         "An entry (conceptual row) representing a set of IP
          Multicast heartbeat parameters.";
        smiv2:oid "1.3.6.1.4.1.9.10.2.1.1.4.1";

        leaf ciscoIpMRouteHeartBeatGroupAddr {
          type inet:ipv4-address;
          description
           "Multicast group address used to receive heartbeat
            packets.";
          smiv2:max-access "not-accessible";
          smiv2:oid "1.3.6.1.4.1.9.10.2.1.1.4.1.1";
        }

        leaf ciscoIpMRouteHeartBeatSourceAddr {
          type inet:ipv4-address;
          description
           "Source address of the last multicast heartbeat packet
            received.";
          smiv2:max-access "read-only";
          smiv2:oid "1.3.6.1.4.1.9.10.2.1.1.4.1.2";
        }

        leaf ciscoIpMRouteHeartBeatInterval {
          type int32 {
            range "10..3600";
          }
          units "seconds";
          description
           "Number of seconds in which a Cisco multicast router
            expects a valid heartBeat packet from a source.  This
            value must be a multiple of 10.";
          smiv2:max-access "read-write";
          smiv2:oid "1.3.6.1.4.1.9.10.2.1.1.4.1.3";
        }

        leaf ciscoIpMRouteHeartBeatWindowSize {
          type int32 {
            range "1..100";
          }
          description
           "Number of ciscoIpMRouteHeartBeatInterval intervals a
            Cisco multicast router waits before checking if expected
            number of heartbeat packets are received or not.";
          smiv2:max-access "read-write";
          smiv2:oid "1.3.6.1.4.1.9.10.2.1.1.4.1.4";
        }

        leaf ciscoIpMRouteHeartBeatCount {
          type yang:gauge32;
          description
           "Number of time intervals where multicast packets were
            received in the last ciscoIpMRouteHeartBeatWindowSize
            intervals.";
          smiv2:max-access "read-only";
          smiv2:oid "1.3.6.1.4.1.9.10.2.1.1.4.1.5";
        }

        leaf ciscoIpMRouteHeartBeatMinimum {
          type int32 {
            range "1..100";
          }
          description
           "The minimal number of heartbeat packets expected in the
            last ciscoIpMRouteHeartBeatWindowSize intervals. If
            ciscoIpMRouteHeartBeatCount falls below this value, an
            SNMP trap/notification, if configured, will be sent to the
            NMS.";
          smiv2:max-access "read-write";
          smiv2:oid "1.3.6.1.4.1.9.10.2.1.1.4.1.6";
        }

        leaf ciscoIpMRouteHeartBeatAlertTime {
          type yang:timestamp;
          description
           "The value of sysUpTime on the most recent occasion at
            which a missing IP multicast heartbeat condition occured
            for the group address specified in this entry.  If no such
            condition have occurred since the last re-initialization
            of the local management subsystem, then this object
            contains a zero value.";
          smiv2:max-access "read-only";
          smiv2:oid "1.3.6.1.4.1.9.10.2.1.1.4.1.7";
        }

        leaf ciscoIpMRouteHeartBeatStatus {
          type snmpv2-tc:RowStatus;
          description
           "This object is used to create a new row or delete an
            existing row in this table.";
          smiv2:max-access "read-write";
          smiv2:oid "1.3.6.1.4.1.9.10.2.1.1.4.1.8";
        }
      }
    }
  }

  smiv2:alias "ciscoIpMRouteTable" {
    description
     "The (conceptual) table containing multicast routing
      information for IP datagrams sent by particular sources to
      the IP multicast groups known to this router. This table is 
      augmented to the ipMRouteTable.";
    smiv2:oid "1.3.6.1.4.1.9.10.2.1.1.2";
  }

  smiv2:alias "ciscoIpMRouteEntry" {
    description
     "An entry (conceptual row) containing the multicast routing
      information for IP datagrams from a particular source and
      addressed to a particular IP multicast group address.";
    smiv2:oid "1.3.6.1.4.1.9.10.2.1.1.2.1";
  }

  augment "/ipmroute-std:IPMROUTE-STD-MIB/ipmroute-std:ipMRouteTable/ipmroute-std:ipMRouteEntry" {
    description
     "An entry (conceptual row) containing the multicast routing
      information for IP datagrams from a particular source and
      addressed to a particular IP multicast group address.";
    smiv2:oid "1.3.6.1.4.1.9.10.2.1.1.2.1";

    leaf ciscoIpMRoutePruneFlag {
      type boolean;
      description
       "Boolean, indicates whether this route is pruned. A pruned
        route is one that has an empty outgoing interface list or
        all interfaces are in Pruned state. A multicast packet
        that matches a pruned route doesn't get forwarded.";
      smiv2:max-access "read-only";
      smiv2:oid "1.3.6.1.4.1.9.10.2.1.1.2.1.12";
    }

    leaf ciscoIpMRouteSparseFlag {
      type boolean;
      description
       "Boolean, indicating PIM multicast routing protocol
        sparse-mode (versus dense-mode).  In sparse-mode, packets
        are forwarded only out interfaces that have been joined.
        In dense-mode, they are forwarded out all interfaces that
        have not been pruned.";
      smiv2:max-access "read-only";
      smiv2:oid "1.3.6.1.4.1.9.10.2.1.1.2.1.13";
    }

    leaf ciscoIpMRouteConnectedFlag {
      type boolean;
      description
       "Boolean, indicating whether there is a directly connected
        member for a group attached to the router.";
      smiv2:max-access "read-only";
      smiv2:oid "1.3.6.1.4.1.9.10.2.1.1.2.1.14";
    }

    leaf ciscoIpMRouteLocalFlag {
      type boolean;
      description
       "Boolean, indicating whether local system is a member of a
        group on any interface.";
      smiv2:max-access "read-only";
      smiv2:oid "1.3.6.1.4.1.9.10.2.1.1.2.1.15";
    }

    leaf ciscoIpMRouteRegisterFlag {
      type boolean;
      description
       "Boolean, indicates whether to send registers for the
        entry. A first hop router directly connected to a
        multicast source host, as well as a border router on the
        boundary of two domains running different multicast
        routing protocols, encapsulates packets to be sent on the
        shared tree. This is done until the RP sends Joins back to
        this router.";
      smiv2:max-access "read-only";
      smiv2:oid "1.3.6.1.4.1.9.10.2.1.1.2.1.16";
    }

    leaf ciscoIpMRouteRpFlag {
      type boolean;
      description
       "Boolean, indicating whether there is a Prune state for
        this source along the shared tree.";
      smiv2:max-access "read-only";
      smiv2:oid "1.3.6.1.4.1.9.10.2.1.1.2.1.17";
    }

    leaf ciscoIpMRouteSptFlag {
      type boolean;
      description
       "Boolean, indicating whether data is being received on the
        SPT tree, ie the Shortest Path Tree.";
      smiv2:max-access "read-only";
      smiv2:oid "1.3.6.1.4.1.9.10.2.1.1.2.1.18";
    }

    leaf ciscoIpMRouteBps {
      type yang:gauge32;
      status deprecated;
      description
       "Bits per second forwarded by this router.  This is the
        sum of all forwarded bits during a 1 second interval.  At
        the end of each second the field is cleared. This object
        has been superseded by ciscoIpMRouteBps2 (which is the
        64-bit version of this object).";
      smiv2:max-access "read-only";
      smiv2:oid "1.3.6.1.4.1.9.10.2.1.1.2.1.19";
    }

    leaf ciscoIpMRouteMetric {
      type int32 {
        range "0..2147483647";
      }
      status deprecated;
      description
       "Metric - The best metric heard from Assert messages. This
        object has been replaced by ciscoIpMRouteMetric2 in order
        to correctly represent a 32-bit unsigned metric value.";
      smiv2:max-access "read-only";
      smiv2:oid "1.3.6.1.4.1.9.10.2.1.1.2.1.20";
    }

    leaf ciscoIpMRouteMetricPreference {
      type int32 {
        range "0..2147483647";
      }
      description
       "Metric Preference - The best metric preference heard from
        Assert messages.";
      smiv2:max-access "read-only";
      smiv2:oid "1.3.6.1.4.1.9.10.2.1.1.2.1.21";
    }

    leaf ciscoIpMRouteInLimit {
      type int32 {
        range "0..2147483647";
      }
      units "Kbits/second";
      status obsolete;
      description
       "Incoming interface's limit for rate limiting data
        traffic, in Kbps. Replaced by ciscoIpMRouteInLimit2.";
      smiv2:max-access "read-only";
      smiv2:oid "1.3.6.1.4.1.9.10.2.1.1.2.1.22";
    }

    leaf ciscoIpMRouteLastUsed {
      type yang:timeticks;
      description
       "How long has it been since the last multicast packet was
        fastswitched.";
      smiv2:max-access "read-only";
      smiv2:oid "1.3.6.1.4.1.9.10.2.1.1.2.1.23";
    }

    leaf ciscoIpMRouteInLimit2 {
      type yang:gauge32;
      units "Kbits/second";
      description
       "Incoming interface's limit for rate limiting data
        traffic, in Kbps.";
      smiv2:max-access "read-only";
      smiv2:oid "1.3.6.1.4.1.9.10.2.1.1.2.1.24";
    }

    leaf ciscoIpMRouteJoinFlag {
      type boolean;
      description
       "Boolean, indicates whether this route is created due to
        SPT threshold.";
      smiv2:max-access "read-only";
      smiv2:oid "1.3.6.1.4.1.9.10.2.1.1.2.1.25";
    }

    leaf ciscoIpMRouteMsdpFlag {
      type boolean;
      description
       "Boolean, indicates whether this route is learned via
        MSDP.";
      smiv2:max-access "read-only";
      smiv2:oid "1.3.6.1.4.1.9.10.2.1.1.2.1.26";
    }

    leaf ciscoIpMRouteProxyJoinFlag {
      type boolean;
      description
       "Boolean, indicates whether to send join for this entry.";
      smiv2:max-access "read-only";
      smiv2:oid "1.3.6.1.4.1.9.10.2.1.1.2.1.27";
    }

    leaf ciscoIpMRoutePkts {
      type yang:counter64;
      description
       "The number of packets which this router has received from
        these sources and addressed to this multicast group
        address. This object is a 64-bit version of ipMRoutePkts.";
      smiv2:max-access "read-only";
      smiv2:oid "1.3.6.1.4.1.9.10.2.1.1.2.1.28";
    }

    leaf ciscoIpMRouteDifferentInIfPkts {
      type yang:counter64;
      description
       "The number of packets which this router has received from
        these sources and addressed to this multicast group
        address, which were not received from the interface
        indicated by ipMRouteInIfIndex. This object is a 64-bit
        version of ipMRouteDifferentInIfPackets.";
      smiv2:max-access "read-only";
      smiv2:oid "1.3.6.1.4.1.9.10.2.1.1.2.1.29";
    }

    leaf ciscoIpMRouteOctets {
      type yang:counter64;
      description
       "The number of octets contained in IP datagrams which were
        received from these sources and addressed to this multicast
        group address, and which were forwarded by this
        router. This object is a 64-bit version of
        ipMRouteOctets.";
      smiv2:max-access "read-only";
      smiv2:oid "1.3.6.1.4.1.9.10.2.1.1.2.1.30";
    }

    leaf ciscoIpMRouteBps2 {
      type yang:gauge64;
      description
       "Bits per second forwarded by this router. This is the sum
        of all forwarded bits during a 1 second interval. At the
        end of each second the field is cleared.";
      smiv2:max-access "read-only";
      smiv2:oid "1.3.6.1.4.1.9.10.2.1.1.2.1.31";
    }

    leaf ciscoIpMRouteMetric2 {
      type uint32;
      description
       "Metric - The best metric heard from Assert messages.";
      smiv2:max-access "read-only";
      smiv2:oid "1.3.6.1.4.1.9.10.2.1.1.2.1.32";
    }
  }

  smiv2:alias "ciscoIpMRouteNextHopTable" {
    description
     "The (conceptual) table containing information on the next
      hops on outgoing interfaces for routing IP multicast
      datagrams.  Each entry is one of a list of next hops on
      outgoing interfaces for particular sources sending to a
      particular multicast group address.";
    smiv2:oid "1.3.6.1.4.1.9.10.2.1.1.3";
  }

  smiv2:alias "ciscoIpMRouteNextHopEntry" {
    description
     "An entry (conceptual row) in the list of next hops on
      outgoing interfaces to which IP multicast datagrams from
      particular sources to a IP multicast group address are
      routed.";
    smiv2:oid "1.3.6.1.4.1.9.10.2.1.1.3.1";
  }

  augment "/ipmroute-std:IPMROUTE-STD-MIB/ipmroute-std:ipMRouteNextHopTable/ipmroute-std:ipMRouteNextHopEntry" {
    description
     "An entry (conceptual row) in the list of next hops on
      outgoing interfaces to which IP multicast datagrams from
      particular sources to a IP multicast group address are
      routed.";
    smiv2:oid "1.3.6.1.4.1.9.10.2.1.1.3.1";

    leaf ciscoIpMRouteNextHopOutLimit {
      type yang:gauge32;
      units "Kbits/second";
      description
       "An outgoing interface's limit for rate limiting data
        traffic, in Kbps.";
      smiv2:max-access "read-only";
      smiv2:oid "1.3.6.1.4.1.9.10.2.1.1.3.1.9";
    }

    leaf ciscoIpMRouteNextHopMacHdr {
      type binary;
      description
       "The data link mac address header for a multicast
        datagram. Used by IP multicast fastswitching.";
      smiv2:max-access "read-only";
      smiv2:oid "1.3.6.1.4.1.9.10.2.1.1.3.1.10";
    }

    leaf ciscoIpMRouteNextHopPkts {
      type yang:counter64;
      description
       "The number of packets which have been forwarded using
        this route. This object is a 64-bit version of
        ipMRouteNextHopPkts.";
      smiv2:max-access "read-only";
      smiv2:oid "1.3.6.1.4.1.9.10.2.1.1.3.1.11";
    }
  }

  smiv2:alias "ciscoIpMRouteInterfaceTable" {
    description
     "The (conceptual) table containing multicast routing
      information specific to interfaces. This table augments
      the ipMRouteInterfaceTable.";
    smiv2:oid "1.3.6.1.4.1.9.10.2.1.1.5";
  }

  smiv2:alias "ciscoIpMRouteInterfaceEntry" {
    description
     "An entry (conceptual row) containing the multicast
      routing information for a particular interface.";
    smiv2:oid "1.3.6.1.4.1.9.10.2.1.1.5.1";
  }

  augment "/ipmroute-std:IPMROUTE-STD-MIB/ipmroute-std:ipMRouteInterfaceTable/ipmroute-std:ipMRouteInterfaceEntry" {
    description
     "An entry (conceptual row) containing the multicast
      routing information for a particular interface.";
    smiv2:oid "1.3.6.1.4.1.9.10.2.1.1.5.1";

    leaf ciscoIpMRouteIfInMcastOctets {
      type yang:counter64;
      description
       "The number of octets of multicast packets that have
        arrived on the interface. This object is a 64-bit version
        of ipMRouteInterfaceInMcastOctets.";
      smiv2:max-access "read-only";
      smiv2:oid "1.3.6.1.4.1.9.10.2.1.1.5.1.1";
    }

    leaf ciscoIpMRouteIfOutMcastOctets {
      type yang:counter64;
      description
       "The number of octets of multicast packets that have been
        sent on the interface. This object is a 64-bit version of
        ipMRouteInterfaceOutMcastOctets.";
      smiv2:max-access "read-only";
      smiv2:oid "1.3.6.1.4.1.9.10.2.1.1.5.1.2";
    }

    leaf ciscoIpMRouteIfInMcastPkts {
      type yang:counter32;
      description
       "The number of multicast packets that have arrived on the
        interface.";
      smiv2:max-access "read-only";
      smiv2:oid "1.3.6.1.4.1.9.10.2.1.1.5.1.3";
    }

    leaf ciscoIpMRouteIfHCInMcastPkts {
      type yang:counter64;
      description
       "The number of multicast packets that have arrived on the
        interface. This object is a 64-bit version of
        ciscoIpMRouteIfInMcastPkts";
      smiv2:max-access "read-only";
      smiv2:oid "1.3.6.1.4.1.9.10.2.1.1.5.1.4";
    }

    leaf ciscoIpMRouteIfOutMcastPkts {
      type yang:counter32;
      description
       "The number of multicast packets that have been sent on
        the interface.";
      smiv2:max-access "read-only";
      smiv2:oid "1.3.6.1.4.1.9.10.2.1.1.5.1.5";
    }

    leaf ciscoIpMRouteIfHCOutMcastPkts {
      type yang:counter64;
      description
       "The number of multicast packets that have been sent on
        the interface. This object is a 64-bit version of
        ciscoIpMRouteIfOutMcastPkts";
      smiv2:max-access "read-only";
      smiv2:oid "1.3.6.1.4.1.9.10.2.1.1.5.1.6";
    }
  }

  notification ciscoIpMRouteMissingHeartBeats {
    description
     "A ciscoIpMRouteMissingHeartBeat is sent if a multicast router
      with this feature enabled failed to receive configured number
      of heartbeat packets from heartbeat sources within a
      configured time interval.";
    smiv2:oid "1.3.6.1.4.1.9.10.2.3.1.0.1";

    container object-1 {

      leaf ciscoIpMRouteHeartBeatGroupAddr {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatGroupAddr";
        }
      }

      leaf ciscoIpMRouteHeartBeatSourceAddr {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatSourceAddr";
        }
      }
    }

    container object-2 {

      leaf ciscoIpMRouteHeartBeatGroupAddr {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatGroupAddr";
        }
      }

      leaf ciscoIpMRouteHeartBeatInterval {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatInterval";
        }
      }
    }

    container object-3 {

      leaf ciscoIpMRouteHeartBeatGroupAddr {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatGroupAddr";
        }
      }

      leaf ciscoIpMRouteHeartBeatWindowSize {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatWindowSize";
        }
      }
    }

    container object-4 {

      leaf ciscoIpMRouteHeartBeatGroupAddr {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatGroupAddr";
        }
      }

      leaf ciscoIpMRouteHeartBeatCount {
        type leafref {
          path "/CISCO-IPMROUTE-MIB:CISCO-IPMROUTE-MIB/CISCO-IPMROUTE-MIB:ciscoIpMRouteHeartBeatTable/CISCO-IPMROUTE-MIB:ciscoIpMRouteHeartBeatEntry/CISCO-IPMROUTE-MIB:ciscoIpMRouteHeartBeatCount";
        }
      }
    }
  }

  smiv2:alias "ciscoIpMRouteMIB" {
    smiv2:oid "1.3.6.1.4.1.9.10.2";
  }

  smiv2:alias "ciscoIpMRouteMIBObjects" {
    smiv2:oid "1.3.6.1.4.1.9.10.2.1";
  }

  smiv2:alias "ciscoIpMRoute" {
    smiv2:oid "1.3.6.1.4.1.9.10.2.1.1";
  }

  smiv2:alias "ciscoIpMRouteMIBConformance" {
    smiv2:oid "1.3.6.1.4.1.9.10.2.2";
  }

  smiv2:alias "ciscoIpMRouteMIBCompliances" {
    smiv2:oid "1.3.6.1.4.1.9.10.2.2.1";
  }

  smiv2:alias "ciscoIpMRouteMIBGroups" {
    smiv2:oid "1.3.6.1.4.1.9.10.2.2.2";
  }

  smiv2:alias "ciscoIpMRouteNotifications" {
    smiv2:oid "1.3.6.1.4.1.9.10.2.3";
  }

  smiv2:alias "ciscoIpMRouteMissingHeartBeatsNotificationPrefix" {
    smiv2:oid "1.3.6.1.4.1.9.10.2.3.1";
  }

  smiv2:alias "ciscoIpMRouteMissingHeartBeatsNotifications" {
    smiv2:oid "1.3.6.1.4.1.9.10.2.3.1.0";
  }

}
