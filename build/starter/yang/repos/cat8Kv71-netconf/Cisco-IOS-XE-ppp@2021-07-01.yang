module Cisco-IOS-XE-ppp {
  namespace "http://cisco.com/ns/yang/Cisco-IOS-XE-ppp";
  prefix ios-ppp;

  import cisco-semver {
    prefix cisco-semver;
  }
  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Point-to-Point Protocol (PPP) Yang model.
     Copyright (c) 2016-2020 by Cisco Systems, Inc.
     All rights reserved.";

  revision 2021-07-01 {
    description
      "- Added tailf annotations to replace tailf:cli-diff-dependency";
    cisco-semver:module-version "4.1.1";
  }
  revision 2021-03-01 {
    description
      "- Added string length, default value for encryption type and cli full no for delete operation for ppp pap";
    cisco-semver:module-version "4.1.0";
  }
  revision 2020-11-01 {
    description
      "- Added support for CLI ppp ipcp address required
       - Added support for ppp link reorder";
    cisco-semver:module-version "4.0.0";
  }
  revision 2020-07-01 {
    description
      "- Added handling of special char in password for ppp chap";
    cisco-semver:module-version "3.0.0";
  }
  revision 2019-11-01 {
    description
      "- Added refine statement";
    cisco-semver:module-version "2.0.0";
  }
  revision 2019-07-01 {
    description
      "- Establish semantic version baseline
       - Added ppp mtu support
       - Added ppp timeout ncp,authentication support under ppp
       - Added multilink test-mode support
       - Added Maximum links option in interface multilink and range for max and min member links";
    cisco-semver:module-version "1.0.0";
  }
  revision 2019-01-31 {
    description
      "Added ppp ipcp route default support";
  }
  revision 2018-11-07 {
    description
      "Cleanup spelling errors in description statements";
  }
  revision 2018-10-16 {
    description
      "Added ppp support for Virtual-PPP interface";
  }
  revision 2018-09-17 {
    description
      "Corrected ppp multilink fragment delay option";
  }
  revision 2018-08-14 {
    description
      "added leafref for multilink member links";
  }
  revision 2018-04-16 {
    description
      "added ppp pap container";
  }
  revision 2018-02-03 {
    description
      "reorder the CLIs, when deleting ppp config under interface serial";
  }
  revision 2017-11-29 {
    description
      "Add disable node for ppp multilink fragment disable";
  }
  revision 2017-02-07 {
    description
      "Initial revision";
  }

  grouping config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping config-multilink-grouping {
    leaf bundle-name {
      description
        "Select method for naming multilink bundles";
      type enumeration {
        enum authenticated;
        enum both;
        enum endpoint;
        enum rfc;
      }
    }
    leaf test-mode {
      description
        "test-mode";
      type uint8 {
        range "0..1";
      }
      default "0";
    }
    leaf virtual-template {
      description
        "virtual-template interface";
      type uint16 {
        range "1..4095";
      }
    }
  }

  grouping config-interface-p2p-multilink-group-common-grouping {
    container links {
      description
        "Specify the limits on the number of links in a bundle";
      container minimum {
        description
          "Minimum number of links desired in the bundle";
        leaf minimum-value {
          type uint8 {
            range "1..16";
          }
          must 'not (../../ios-ppp:maximum/ios-ppp:maximum-value) or(current() <= ../../ios-ppp:maximum/ios-ppp:maximum-value)' {
            error-message " Minimum must be less than or equal to maximum";
          }
        }
        leaf mandatory {
          description
            "Disable network layer until minimum number of links is reach";
          type empty;
        }
      }
      container maximum {
        description
          "Maximum number of links allowed in the bundle";
        leaf maximum-value {
          type uint8 {
            range "1..16";
          }
          must 'not (../../ios-ppp:minimum/ios-ppp:minimum-value) or(current() >= ../../ios-ppp:minimum/ios-ppp:minimum-value)' {
            error-message " Maximum must be more than or equal to minimum";
          }
        }
      }
    }
    container endpoint {
      description
        "Configure the local Endpoint Discriminator";
      leaf string {
        description
          "Use specified string";
        type string;
      }
    }
    container fragment {
      description
        "Specify fragmentation parameters";
      container delay {
        description
          "Specify the maximum delay for each fragment";
        leaf delay-value {
          type uint16 {
            range "0..1000";
          }
        }
        leaf additional-delay-value {
          type uint16 {
            range "1..999";
          }
        }
      }
      leaf disable {
        description
          "Suppress multilink fragmentation when possible";
        type empty;
      }
    }
    leaf interleave {
      description
        "Allow interleaving of small packets with fragments";
      type empty;
    }
  }

  grouping config-interface-p2p-multilink-group-create-grouping {
    container multilink {
      description
        "Make interface multilink capable";
      presence "true";
      uses config-interface-p2p-multilink-group-common-grouping;
      leaf group {
        description
          "Put interface in a multilink bundle";
        type uint32 {
          range "1..2147483647";
        }
      }
    }
  }

  grouping config-interface-p2p-multilink-group-use-grouping {
    container multilink {
      description
        "Make interface multilink capable";
      presence "true";
      uses config-interface-p2p-multilink-group-common-grouping;
      leaf group {
        description
          "Put interface in a multilink bundle";
        type leafref {
          path "/ios:native/ios:interface/ios:Multilink/ios-ppp:ppp/ios-ppp:multilink/ios-ppp:group";
        }
      }
    }
  }

  grouping config-interface-p2p-options-grouping {
    leaf accounting {
      description
        "Set PPP network accounting method";
      type union {
        type string;
        type enumeration {
          enum default;
        }
      }
    }
    container chap {
      description
        "Set CHAP authentication parameters";
      leaf hostname {
        description
          "Set alternate CHAP hostname";
        type string;
      }
      container challenge-length {
        description
          "Challenge Length for CHAP";
        leaf minimum {
          description
            "Minimum length for CHAP challenge";
          type uint8 {
            range "16..63";
          }
        }
        leaf maximum {
          description
            "Maximum length for CHAP challenge";
          when '../minimum';
          type uint8 {
            range "16..63";
          }
        }
      }
      container password {
        description
          "Set default CHAP password";
        leaf enryption-type {
          description
            "Encryption type (0=not yet encrypted) (7=encrypted) password";
          type enumeration {
            enum 0;
            enum 7;
          }
        }
        leaf ppp-auth-password {
          description
            "Default PPP authentication password";
          type string {
            pattern '.*';
          }
        }
      }
    }
    container pap {
      description
        "Set PAP authentication parameters";
      container refuse {
        description
          "Refuse to authenticate using PAP";
        presence "true";
        leaf callin {
          description
            "Refuse to authenticate on incoming call only";
          type empty;
        }
      }
      container sent-username {
        description
          "Set Outbound PAP username";
        container username {
          description
            "Outbound PAP username";
          leaf username-string {
            description
              "Outbound PAP username";
            type string;
          }
          leaf password {
            description
              "Set outbound PAP password";
            type empty;
          }
          leaf enryption-type {
            description
              "Encryption type (0=not yet encrypted) (7=encrypted) password";
            when '../password';
            type enumeration {
              enum 0;
              enum 7;
            }
            default "0";
          }
          leaf ppp-auth-password {
            description
              "Outbound PAP password";
            when '../password';
            type string {
              length "1..215";
            }
          }
        }
      }
      leaf wait {
        description
          "Wait for caller to authenticate first";
        type empty;
      }
    }
    container authentication {
      description
        "Set PPP link authentication method";
      leaf method {
        type enumeration {
          enum chap;
          enum eap;
          enum ms-chap;
          enum ms-chap-v2;
          enum pap;
        }
      }
      leaf chap {
        description
          "Challenge Handshake Authentication Protocol (CHAP)";
        when "../method and not(../method = 'chap')";
        type empty;
      }
      leaf eap {
        description
          "Extensible Authentication Protocol (EAP)";
        when "../method and not(../method = 'eap')";
        type empty;
      }
      leaf ms-chap {
        description
          "Microsoft Challenge Handshake Authentication Protocol (MS-CHAP)";
        when "../method and not(../method = 'ms-chap')";
        type empty;
      }
      leaf ms-chap-v2 {
        description
          "Microsoft CHAP Version 2 (MS-CHAP-V2)";
        when "../method and not(../method = 'ms-chap-v2')";
        type empty;
      }
      leaf pap {
        description
          "Password Authentication Protocol (PAP)";
        when "../method and not(../method = 'pap')";
        type empty;
      }
      leaf callback {
        description
          "Authenticate remote on callback only";
        when '../method';
        type empty;
      }
      leaf callin {
        description
          "Authenticate remote on incoming call only";
        when '../method';
        type empty;
      }
      leaf callout {
        description
          "Authenticate remote on outgoing call only";
        when '../method';
        type empty;
      }
      leaf optional {
        description
          "Allow peer to refuse to authenticate";
        type empty;
      }
      leaf list-name {
        type string;
      }
      leaf default {
        description
          "Use the default authentication list";
        type empty;
      }
      leaf one-time {
        description
          "Allow use of username*OTP for one-time passwords";
        type empty;
      }
    }
    leaf authorization {
      description
        "Set PPP network authorization method";
      type union {
        type string;
        type enumeration {
          enum default;
        }
      }
    }
    container ipcp {
      description
        "Set IPCP negotiation options";
      container mask {
        description
          "Specify DNS mask";
        leaf request {
          description
            "Request server address mask";
          type empty;
        }
      }
      container dns {
        description
          "Specify DNS negotiation options";
        container primary {
          description
            "Primary DNS IP address";
          leaf primary-dns-address {
            description
              "Primary DNS IP address";
            type inet:ipv4-address;
          }
          leaf secondary-dns-address {
            description
              "Secondary DNS IP address";
            type inet:ipv4-address;
          }
          leaf aaa {
            description
              "Use DNS data from AAA";
            type empty;
          }
          leaf accept {
            description
              "Accept any non zero DNS address";
            type empty;
          }
        }
        leaf accept {
          description
            "Accept any non zero DNS address";
          type empty;
        }
        leaf reject {
          description
            "Reject negotiations with the peer";
          type empty;
        }
        container request {
          description
            "Request server addresses from peer";
          presence "true";
          leaf accept {
            description
              "Accept any non zero DNS address";
            type empty;
          }
        }
      }
      container wins {
        description
          "Specify WINS negotiation options";
        container primary {
          description
            "Primary WINS IP address";
          leaf primary-wins-address {
            description
              "Primary WINS IP address";
            type inet:ipv4-address;
          }
          leaf secondary-wins-address {
            description
              "Secondary WINS IP address";
            type inet:ipv4-address;
          }
          leaf aaa {
            description
              "Use WINS data from AAA";
            type empty;
          }
          leaf accept {
            description
              "Accept any non zero WINS address";
            type empty;
          }
        }
        leaf accept {
          description
            "Accept any non zero WINS address";
          type empty;
        }
        leaf reject {
          description
            "Reject negotiations with the peer";
          type empty;
        }
        container request {
          description
            "Request server addresses from peer";
          presence "true";
          leaf accept {
            description
              "Accept any non zero WINS address";
            type empty;
          }
        }
      }
      container route {
        description
          "Install default route through negotiated peer IP address";
        leaf default {
          description
            "Install default route through negotiated peer IP address";
          type empty;
        }
      }
      container address {
        description
          "Additional ipcp address options";
        leaf required {
          description
            "Disconnect peers with no IP address negotiated";
          type empty;
        }
      }
    }
    container timeout {
      description
        "Set PPP timeout parameters";
      when '../../ios:encapsulation/ios:ppp';
      container ncp {
        description
          "Maximum time to wait for network layer to negotiate";
        leaf ncp-timeout {
          description
            "Maximum time to wait for network layer to negotiate in seconds";
          type uint16 {
            range "1..65535";
          }
        }
        leaf termination {
          description
            "Maximum time to wait for renegotiation after NCP termination";
          type uint16 {
            range "1..65535";
          }
        }
      }
      leaf authentication {
        description
          "Maximum time to wait for an authentication response";
        type uint8 {
          range "0..255";
        }
      }
    }
    container mtu {
      description
        "PPP MTU configuration";
      container adaptive {
        description
          "Adapt MTU to peer's MRU";
        presence "true";
        leaf proxy {
          description
            "Adapt MTU to proxy MRU";
          type empty;
        }
      }
      container pppoe {
        description
          "Remove 1492 byte upper limit on MTU for PPPoE session";
        leaf unlimited {
          description
            "MTU PPPoE related subcommands";
          type empty;
        }
      }
    }
    container link {
      description
        "PPP link configuration";
      leaf reorders {
        description
          "PPP link reordering";
        type empty;
      }
    }
  }

  grouping config-interface-p2p-grouping {
    container ppp {
      description
        "Point-to-Point Protocol";
      uses config-interface-p2p-options-grouping;
    }
  }

  grouping config-interface-encap-depend-p2p-grouping {
    container ppp {
      description
        "Point-to-Point Protocol";
      when '../ios:encapsulation/ios:ppp';
      uses config-interface-p2p-options-grouping;
    }
  }

  augment "/ios:native/ios:ppp" {
    uses config-ppp-grouping;
  }

  augment "/ios:native/ios:multilink" {
    uses config-multilink-grouping {
      if-feature "ios-features:multilink";
    }
  }

  augment "/ios:native/ios:interface/ios:Multilink" {
    uses config-interface-p2p-grouping {
      if-feature "ios-features:multilink";
    }
  }

  augment "/ios:native/ios:interface/ios:Multilink/ios-ppp:ppp" {
    uses config-interface-p2p-multilink-group-create-grouping {
      if-feature "ios-features:multilink";
      refine "multilink/group" {
        must '../../../ios:name=current()' {
          error-message "%  Cannot add multilink-group interface to a different multilink group";
        }
      }
    }
  }

  augment "/ios:native/ios:interface/ios:Serial" {
    uses config-interface-encap-depend-p2p-grouping {
      if-feature "ios-features:multilink";
    }
  }

  augment "/ios:native/ios:interface/ios:Serial/ios-ppp:ppp" {
    uses config-interface-p2p-multilink-group-use-grouping {
      if-feature "ios-features:multilink";
    }
  }

  augment "/ios:native/ios:interface/ios:Virtual-Template" {
    uses config-interface-p2p-grouping {
      if-feature "ios-features:multilink";
    }
  }

  augment "/ios:native/ios:interface/ios:Virtual-Template/ios-ppp:ppp" {
    status obsolete;
    uses config-interface-p2p-multilink-group-use-grouping {
      if-feature "ios-features:multilink";
      status obsolete;
    }
  }

  augment "/ios:native/ios:interface/ios:Virtual-PPP" {
    uses config-interface-p2p-grouping {
      if-feature "ios-features:multilink";
    }
  }

  augment "/ios:native/ios:interface/ios:Dialer" {
    uses config-interface-encap-depend-p2p-grouping {
      if-feature "ios-features:multilink";
    }
  }

  augment "/ios:native/ios:interface/ios:Dialer/ios-ppp:ppp" {
    uses config-interface-p2p-multilink-group-create-grouping {
      if-feature "ios-features:multilink";
    }
  }
}
