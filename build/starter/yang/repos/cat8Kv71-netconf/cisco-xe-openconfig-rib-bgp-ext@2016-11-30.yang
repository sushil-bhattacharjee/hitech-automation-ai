module cisco-xe-openconfig-rib-bgp-ext {

  yang-version "1";

  // namespace
  namespace "http://cisco.com/ns/yang/cisco-xe-openconfig-rib-bgp-ext";

  prefix "cisco-bgprib";

  import openconfig-rib-bgp {
    prefix "oc-bgp-rib";
  }

  import openconfig-network-instance {
    prefix "oc-ni";
  }


 organization
    "Cisco Systems, Inc.";

  contact
    "Cisco Systems, Inc. Customer Service Postal: 170 W Tasman Drive
     San Jose, CA 95134 Tel: +1 1800 553-NETS E-mail: cs-yang@cisco.com";

  description
    "TBD"+
    "Copyright (c) 2016 by Cisco Systems, Inc."+
    "All rights reserved.";

  revision 2016-11-30 {
    description
      "Initial version";
    reference "openconfig-rib-bgp.yang";
  }


augment "/oc-ni:network-instances/oc-ni:network-instance/oc-ni:protocols/oc-ni:protocol" {
    description
      "Adds the BGP-RIB to Network Instance";

    uses oc-bgp-rib:bgp-rib-top;
  }

 // IPv4 augments

  augment "/oc-ni:network-instances/oc-ni:network-instance/oc-ni:protocols/oc-ni:protocol/bgp-rib/afi-safis/afi-safi/ipv4-unicast/loc-rib" {
    description
        "Adds the IPv4 route list to the IPv4-unicast tables";

    uses oc-bgp-rib:ipv4-routes;
  }

  augment "/oc-ni:network-instances/oc-ni:network-instance/oc-ni:protocols/oc-ni:protocol/bgp-rib/afi-safis/afi-safi/ipv4-unicast/neighbors/" +
    "neighbor/adj-rib-in-pre" {
    description
        "Adds the IPv4 route list to the IPv4-unicast tables";

    uses oc-bgp-rib:ipv4-routes;
  }

  augment "/oc-ni:network-instances/oc-ni:network-instance/oc-ni:protocols/oc-ni:protocol/bgp-rib/afi-safis/afi-safi/ipv4-unicast/neighbors/" +
    "neighbor/adj-rib-in-post" {
    description
        "Adds the IPv4 route list to the IPv4-unicast tables";

    uses oc-bgp-rib:ipv4-routes;
  }

  augment "/oc-ni:network-instances/oc-ni:network-instance/oc-ni:protocols/oc-ni:protocol/bgp-rib/afi-safis/afi-safi/ipv4-unicast/neighbors/" +
    "neighbor/adj-rib-out-pre" {
    description
      "Adds the IPv4 route list to the IPv4-unicast tables";

    uses oc-bgp-rib:ipv4-routes;
  }

  augment "/oc-ni:network-instances/oc-ni:network-instance/oc-ni:protocols/oc-ni:protocol/bgp-rib/afi-safis/afi-safi/ipv4-unicast/neighbors/" +
    "neighbor/adj-rib-out-post" {
    description
      "Adds the IPv4 route list to the IPv4-unicast tables";

    uses oc-bgp-rib:ipv4-routes;
  }

  // IPv6 augments

  augment "/oc-ni:network-instances/oc-ni:network-instance/oc-ni:protocols/oc-ni:protocol/bgp-rib/afi-safis/afi-safi/ipv6-unicast/loc-rib" {
    description
      "Adds the IPv6 route list to the IPv6-unicast tables";
    uses oc-bgp-rib:ipv6-routes;
  }

  augment "/oc-ni:network-instances/oc-ni:network-instance/oc-ni:protocols/oc-ni:protocol/bgp-rib/afi-safis/afi-safi/ipv6-unicast/neighbors/" +
    "neighbor/adj-rib-in-pre" {
    description
      "Adds the IPv6 route list to the IPv6-unicast tables";

      uses oc-bgp-rib:ipv6-routes;
  }

  augment "/oc-ni:network-instances/oc-ni:network-instance/oc-ni:protocols/oc-ni:protocol/bgp-rib/afi-safis/afi-safi/ipv6-unicast/neighbors/" +
    "neighbor/adj-rib-in-post" {
    description
      "Adds the IPv6 route list to the IPv6-unicast tables";

    uses oc-bgp-rib:ipv6-routes;
  }

  augment "/oc-ni:network-instances/oc-ni:network-instance/oc-ni:protocols/oc-ni:protocol/bgp-rib/afi-safis/afi-safi/ipv6-unicast/neighbors/" +
    "neighbor/adj-rib-out-pre" {
    description
      "Adds the IPv6 route list to the IPv6-unicast tables";

    uses oc-bgp-rib:ipv6-routes;
  }

  augment "/oc-ni:network-instances/oc-ni:network-instance/oc-ni:protocols/oc-ni:protocol/bgp-rib/afi-safis/afi-safi/ipv6-unicast/neighbors/" +
    "neighbor/adj-rib-out-post" {
    description
      "Adds the IPv6 route list to the IPv6-unicast tables";

    uses oc-bgp-rib:ipv6-routes;
  }
}
