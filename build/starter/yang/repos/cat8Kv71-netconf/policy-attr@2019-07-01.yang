module policy-attr {
  yang-version 1;
  namespace "urn:ietf:params:xml:ns:yang:policy-attr";
  prefix policy-attr;

  import cisco-semver {
    prefix cisco-semver;
  }
  import ietf-yang-types {
    prefix yang;
  }
  import ietf-inet-types {
    prefix inet;
  }
  import policy-types {
    prefix policy-types;
  }

  organization
    "Cisco Systems, Inc.";
  contact
    "Cisco Systems, Inc.
     Customer Service

     Postal: 170 W Tasman Drive
     San Jose, CA 95134

     Tel: +1 1800 553-NETS

     E-mail: cs-yang@cisco.com

     Editor:   Nazanin Magharei
               <mailto:nmaghare@cisco.com>";
  description
    "This module contains a collection of YANG groupings
     in filter configurations for policy model.";

  revision 2019-07-01 {
    description
      "Establish semantic version baseline";
    cisco-semver:module-version "1.0.0";
  }
  revision 2015-04-27 {
    description
      "First revision";
    reference
      "TBD";
  }

  grouping dscp-cfg {
    description
      "DSCP configuration.";
    leaf dscp-min {
      type policy-types:dscp-type;
      description
        "min dscp value ";
    }
    leaf dscp-max {
      type policy-types:dscp-type;
      description
        "max dscp value ";
    }
  }

  grouping cos-cfg {
    description
      "cos configuration.";
    leaf cos-min {
      type policy-types:cos-type;
      description
        "min cos value ";
    }
    leaf cos-max {
      type policy-types:cos-type;
      description
        "min cos value ";
    }
  }

  grouping src-dst-ip-cfg {
    description
      "Source or destination IP";
    leaf src-dst-ip-addr {
      type policy-types:src-dst-ip-type;
      description
        "source or destination IP value";
    }
  }

  grouping src-dst-port-cfg {
    description
      "Source or destination port";
    leaf src-dst-port-min {
      type policy-types:src-dst-port-type;
      description
        "min source or destination port value";
    }
    leaf src-dst-port-max {
      type policy-types:src-dst-port-type;
      description
        "max source or destination port value";
    }
  }

  grouping protocol-cfg {
    description
      "Match Protocol configuration";
    leaf protocol-name {
      type policy-types:protocol-type;
      description
        "Name of the protocol used
         as a matching criterion. Supported protocols
         include the following:
         aarp : AppleTalk Address Resolution Protocol
         apollo : Apollo Domain
         arp : IP Address Resolution Protocol (ARP)
         bridge : bridging
         bstun : Block Serial Tunneling
         cdp : Cisco Discovery Protocol
         clns : ISO Connectionless Network Service
         clns_es : ISO CLNS End System
         clns_is : ISO CLNS Intermediate System
         cmns : ISO Connection-Mode Network Service
         compressedtcp : compressed TCP
         decnet : DECnet
         decnet_node : DECnet Node
         decnet_router-I1 : DECnet Router L1
         decnet_router-I2 : DECnet Router L2
         dlsw : data-link switching
         ip:IP
         ipx:Novell IPX
         llc2:llc2
         pad:packet assembler/disassembler links
         qllc:Qualified Logical Link Control protocol
         rsrb:remote source-route bridging
         snapshot:snapshot routing support
         stun:serial tunnel
         vines:Banyan VINES
         xns:Xerox Network Services";
    }
  }

  grouping protocol-name-cfg {
    description
      "Match Protocol configuration";
    leaf protocol-name {
      type policy-types:protocol-name;
      description
        "protocol name";
    }
  }

  grouping ip-acl-name-cfg {
    description
      "IP ACL name configuration";
    leaf ip-acl-name {
      type policy-types:ip-acl-name-type;
      description
        "IP ACL name";
    }
  }

  grouping ip-acl-cfg {
    description
      "IP ACL number configuration";
    leaf ip-acl {
      type policy-types:ip-acl-type;
      description
        "IP ACL number";
    }
  }

  grouping input-interface-cfg {
    description
      "Input interface configuration";
    leaf if-name {
      type string {
        length "1..255";
      }
      description
        "Input interface ID";
    }
  }

  grouping dei-cfg {
    description
      "DEI bit configuration";
    leaf dei-cfg {
      type policy-types:dei-type;
      description
        "DEI bit value";
    }
  }

  grouping flow-cfg {
    description
      "Flow configuration";
    leaf flow-src-ip {
      type inet:ip-address-no-zone;
      description
        "Flow source IP";
    }
    leaf flow-dst-ip {
      type inet:ip-address-no-zone;
      description
        "Flow destination IP";
    }
    leaf protocol {
      type inet:ip-version;
      description
        "FLOW IP protocol";
    }
    leaf src-port {
      type inet:port-number;
      description
        "Flow source port number";
    }
    leaf dst-port {
      type inet:port-number;
      description
        "Flow destination port number";
    }
  }

  grouping flow-record-cfg {
    description
      "Flow record configuration";
    leaf flow-record-name {
      type policy-types:flow-record-type;
      description
        "Flow record type";
    }
  }

  grouping fr-de-cfg {
    description
      "Frame Relay DE configuration";
    leaf fr-de-val {
      type policy-types:fr-de-type;
      description
        "Frame Relay DE type";
    }
  }

  grouping wlan-user-priority-cfg {
    description
      "WLAN user priority configuration";
    leaf wlan-prio-min {
      type policy-types:wlan-user-priority-type;
      description
        "WLAN user priority minimum";
    }
    leaf wlan-prio-max {
      type policy-types:wlan-user-priority-type;
      description
        "Wlan user priority maximum";
    }
  }

  grouping discard-class-cfg {
    description
      "";
    leaf discard-class {
      type policy-types:discard-class-type;
      description
        "";
    }
  }

  grouping class-map-cfg {
    description
      "";
    leaf class-map-name {
      type policy-types:class-map-type;
      description
        "";
    }
  }

  grouping application-cfg {
    description
      "";
    leaf application-name {
      type policy-types:application-type;
      description
        "";
    }
    leaf application-cfg {
      type policy-types:application-type;
      description
        "";
    }
  }

  grouping mac-cfg {
    description
      "Mac address configuration";
    leaf mac {
      type yang:mac-address;
      description
        "Specifies the source/destination MAC address
         to be used as a match criterion.";
    }
    leaf mac-mask {
      type yang:mac-address;
      description
        "Specifies the source/destination MAC address
         mask to be used as a match criterion.";
    }
  }

  grouping mpls-exp-cfg {
    description
      "Specified value of the MPLS EXP field
       configuration.";
    leaf exp-min {
      type policy-types:mpls-exp-type;
      description
        "The minimum EXP field value to be used as
         match criteria. Any number from 0 to 7.";
    }
    leaf exp-max {
      type policy-types:mpls-exp-type;
      description
        "The maximum EXP field value to be used as
         match criteria. Any number from 0 to 7.";
    }
  }

  grouping pkt-len-cfg {
    description
      "Specifies the Layer 3 packet length
       configuration";
    leaf min-pkt-len {
      type policy-types:pkt-len-type;
      description
        "Minimum layer 3 packet length in bytes.";
    }
    leaf max-pkt-len {
      type policy-types:pkt-len-type;
      description
        "Maximum layer 3 packet length in bytes.";
    }
  }

  grouping prec-val-cfg {
    description
      "Specifies the exact value from 0 to 7 used to
       identify an IP precedence value.";
    leaf prec-val {
      type policy-types:prec-val-type;
      description
        "Value from 0 to 7 used to identify an
         IP precedence value.";
    }
  }

  grouping prec-attr-cfg {
    description
      "IP precedence configuration";
    leaf prec-attr {
      type policy-types:prec-attr-type;
      description
        "IP precedence attribute:
         critical   Match packets with critical precedence (5)
         flash      Match packets with flash precedence (3)
         flash-override  Match packets with flash override precedence (4)
         immediate  Match packets with immediate precedence (2)
         internet   Match packets with internetwork control precedence (6)
         network    Match packets with network control precedence (7)
         priority   Match packets with priority precedence (1)
         routine    Match packets with routine precedence (0)
        ";
    }
  }

  grouping qos-group-cfg {
    description
      "QOS group configuration";
    leaf qos-group-min {
      type policy-types:qos-group-type;
      description
        "Specifies the minimum value range from 0 to
         99 used to identify a QoS group value.";
    }
    leaf qos-group-max {
      type policy-types:qos-group-type;
      description
        "Specifies the maximum value range from 0 to
         99 used to identify a QoS group value.";
    }
  }

  grouping vlan-cfg {
    description
      "Vlan configuration";
    leaf vlan-min {
      type policy-types:vlan-type;
      description
        "Vlan minimum ID";
    }
    leaf vlan-max {
      type policy-types:vlan-type;
      description
        "Vlan maximum ID";
    }
  }

  grouping atm-vci-cfg {
    description
      "ATM VCI configuration";
    leaf atm-vci-min {
      type uint16 {
        range "32..65535";
      }
      description
        "ATM VCI minimum value";
    }
    leaf atm-vci-max {
      type uint16 {
        range "32..65535";
      }
      description
        "ATM VCI maximum value";
    }
  }

  grouping atm-clp-cfg {
    description
      "ATM CLP configuration";
    leaf atm-clp {
      type empty;
      description
        "ATM CLP activation";
    }
  }

  grouping ip-rtp-cfg {
    description
      "Real-Time Protocol (RTP) protocol
       port number configuration.";
    leaf starting-port-number {
      type uint16 {
        range "2000..65535";
      }
      description
        "The starting RTP port number.
         Values range from 2000 to 65535.";
    }
    leaf port-range {
      type uint16 {
        range "2000..65535";
      }
      description
        "The RTP port number range.
         Values range from 0 to 16383.";
    }
  }

  grouping fr-dlci-cfg {
    description
      "Frame Relay DLCI configuration";
    leaf dlci-min {
      type uint16 {
        range "16..1007";
      }
      description
        "Frame Relay DLCI minimum value";
    }
    leaf dlci-max {
      type uint16 {
        range "16..1007";
      }
      description
        "Frame Relay DLCI maximum value";
    }
  }

  grouping metadata-cfg {
    description
      "Metadata configuration";
    leaf cac {
      type enumeration {
        enum addmitted;
        enum un-addmitted;
      }
      description
        "Metadata CAC value";
    }
    leaf called-uri {
      type string;
      description
        "Metadata called-uri value";
    }
    leaf calling-uri {
      type string;
      description
        "Metadata calling-uri value";
    }
    leaf device-model {
      type string;
      description
        "Metadata device-model value";
    }
    leaf global-session-id {
      type string;
      description
        "Metadata global session ID";
    }
    leaf multi-party-session-id {
      type string;
      description
        "Metadata multi-party-session ID";
    }
  }

  grouping security-group-name-cfg {
    description
      "Security group name configuration";
    leaf src-dst {
      type enumeration {
        enum source;
        enum destination;
      }
      description
        "Security group name source and
         destination values";
    }
    leaf security-name {
      type string;
      description
        "Security group name value";
    }
  }

  grouping security-group-tag-cfg {
    description
      "Security group tag ID configuration";
    leaf id {
      type string;
      description
        "Security group tag ID";
    }
  }

  grouping vpls-cfg {
    description
      "VPLS configuration";
    leaf broadcast {
      type empty;
      description
        "Broadcast value";
    }
    leaf known {
      type empty;
      description
        "Known value";
    }
    leaf unknown {
      type empty;
      description
        "Unknown value";
    }
    leaf multicast {
      type empty;
      description
        "Multicast value";
    }
  }
}
