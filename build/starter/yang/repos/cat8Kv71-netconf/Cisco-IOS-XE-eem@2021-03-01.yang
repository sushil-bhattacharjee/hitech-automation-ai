module Cisco-IOS-XE-eem {
  namespace "http://cisco.com/ns/yang/Cisco-IOS-XE-eem";
  prefix ios-eem;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Embedded Event Manager (EEM) Yang model.
     Copyright (c) 2016-2020 by Cisco Systems, Inc.
     All rights reserved.";

  revision 2021-03-01 {
    description
      "
       - Added hardening changes for the following clis
       - Event syslog pattern,max-run,ratelimit,occurs,period
       - event timer cron,watchdog max-run,ratelimit for each timer
       - event ipsla reaction-type, group name, max-run,ratelimit
       - event routing network ipv4/ipv6, type, max-run,ratelimit
       - Event none max-run,ratelimit
       - Action syslog msg
       - action wait
       - action regular expression pattern, input, match, other matches
       - action reload";
    cisco-semver:module-version "2.1.0";
  }
  revision 2020-11-01 {
    description
      "-Hardening of the following clis
       -event manager session cli username
       -action label cli command
       -event manager applet
       -event manager track";
    cisco-semver:module-version "2.0.0";
  }
  revision 2019-07-01 {
    description
      "Establish semantic version baseline";
    cisco-semver:module-version "1.0.0";
  }
  revision 2018-09-14 {
    description
      "support eem wait option";
  }
  revision 2017-12-20 {
    description
      "fix applet resource configuration";
  }
  revision 2017-11-20 {
    description
      "fix event oir event removal";
  }
  revision 2017-09-20 {
    description
      "Add some applet event support";
  }
  revision 2017-08-03 {
    description
      "Add event time full support";
  }
  revision 2017-04-13 {
    description
      "Add event track";
  }
  revision 2017-04-10 {
    description
      "Add cli command and exit for action";
  }
  revision 2017-02-07 {
    description
      "Initial revision";
  }

  typedef operator-type {
    type enumeration {
      enum eq;
      enum ge;
      enum gt;
      enum le;
      enum lt;
      enum ne;
    }
  }

  grouping eem-default-group {
    leaf default {
      description
        "Default action timer";
      type uint32;
    }
  }

  grouping eem-maxrun-group {
    leaf maxrun {
      description
        "Maximum runtime of applet";
      type uint32 {
        range "0..31536000";
      }
    }
  }

  grouping eem-set-maxrun-group {
    leaf maxrun {
      description
        "Maximum runtime of applet";
      type uint32 {
        range "0..31536000";
      }
    }
  }

  grouping eem-ratelimit-group {
    leaf ratelimit {
      description
        "seconds[.milliseconds] value";
      type uint32 {
        range "0..31536000";
      }
    }
  }

  grouping eem-set-ratelimit-group {
    leaf ratelimit {
      description
        "Limit trigger to once per given time period";
      type uint32 {
        range "0..31536000";
      }
    }
  }

  grouping eem-timer-cron-group {
    uses eem-maxrun-group;
    leaf name {
      description
        "Timer name string";
      type string;
    }
    uses eem-ratelimit-group;
    leaf cron-entry {
      description
        "Cron entry for cron timer";
      type string;
    }
  }

  grouping eem-timer-common-group {
    uses eem-maxrun-group;
    leaf name {
      description
        "Timer name string";
      type string;
    }
    uses eem-ratelimit-group;
    leaf time {
      description
        "Time period for watchdog / countdown / absolute timer";
      type uint32 {
        range "1..2085978494";
      }
    }
  }

  grouping config-eem-grouping {
    container manager {
      description
        "Event Manager configuration commands";
      list environment {
        description
          "Set an Embedded Event Manager global environment variable";
        key "name";
        leaf name {
          type string;
        }
        leaf value {
          type string;
        }
      }
      container directory {
        description
          "Set Embedded Event Manager directory information";
        container user {
          description
            "Set Embedded Event Manager user directory information";
          leaf policy {
            description
              "Set Embedded Event Manager user policy directory";
            type string;
          }
        }
      }
      container session {
        description
          "Set Embedded Event Manager session attributes";
        container cli {
          description
            "Set Embedded Event Manager session cli attributes";
          container username {
            description
              "Set username used in Embedded Event Manager cli sessions";
            list username_in_word {
              max-elements 1;
              key "username_in_word";
              leaf username_in_word {
                description
                  "username";
                type string {
                  length "1..64";
                }
              }
              leaf privilege {
                description
                  "Set user privilege level";
                type uint8 {
                  range "0..15";
                }
                default "1";
              }
            }
          }
        }
      }
      list applet {
        description
          "Register an Event Manager applet";
        key "name";
        leaf name {
          description
            "Name of the Event Manager applet";
          type string;
        }
        leaf authorization {
          description
            "Specify an authorization type for the applet";
          type enumeration {
            enum bypass;
          }
        }
        leaf class {
          description
            "Specify a class for the applet";
          type string {
            pattern '[A-Z]|default';
          }
        }
        leaf trap {
          description
            "Generate an SNMP trap when applet is triggered.";
          type empty;
        }
        container event {
          description
            "Add or modify event information";
          choice event-option {
            container timer-choice {
              description
                "Timer event";
              container absolute {
                description
                  "Absolute timer event";
                uses eem-timer-common-group;
              }
              container countdown {
                description
                  "Countdown timer event";
                uses eem-timer-common-group;
              }
              container cron {
                description
                  "cron timer event";
                uses eem-timer-cron-group;
              }
              container watchdog {
                description
                  "Watchdog timer event";
                uses eem-timer-common-group;
              }
            }
            container syslog-choice {
              description
                "Syslog event";
              leaf occurs {
                description
                  "Number of occurrences before raising event";
                type uint32 {
                  range "1..32";
                }
              }
              leaf pattern {
                description
                  "Pattern match string for the entire message";
                type string;
              }
              leaf period {
                description
                  "Occurrence period";
                type uint32 {
                  range "0..4294967295";
                }
              }
              uses eem-set-maxrun-group;
              uses eem-set-ratelimit-group;
            }
            container track-choice {
              description
                "Tracking object event";
              leaf track-object-number {
                description
                  "Tracking object number";
                type uint16 {
                  range "1..1000";
                }
              }
              leaf state {
                description
                  "State of tracking object";
                when '../track-object-number';
                type enumeration {
                  enum any;
                  enum down;
                  enum up;
                }
                default "any";
              }
              uses eem-set-maxrun-group;
              uses eem-set-ratelimit-group;
            }
            container none-choice {
              description
                "Manually run policy event";
              presence "true";
              uses eem-default-group;
              uses eem-maxrun-group;
              uses eem-ratelimit-group;
              leaf sync {
                description
                  "EEM policy execution sync or async";
                type enumeration {
                  enum yes;
                  enum no;
                }
              }
            }
            container ipsla {
              description
                "IPSLA Event";
              leaf group-name {
                description
                  "IPSLA Group Name";
                type string;
              }
              leaf reaction-type {
                description
                  "IPSLA Reaction Type";
                type enumeration {
                  enum connectionLoss;
                  enum icpif;
                  enum jitterAvg;
                  enum jitterDSAvg;
                  enum jitterSDAvg;
                  enum maxOfNegativeDS;
                  enum maxOfNegativeSD;
                  enum maxOfPositiveDS;
                  enum maxOfPositiveSD;
                  enum mos;
                  enum packetLateArrival;
                  enum packetLossDS;
                  enum packetLossSD;
                  enum packetMIA;
                  enum packetOutOfSequence;
                  enum rtt;
                  enum timeout;
                  enum verifyError;
                }
              }
              uses eem-set-maxrun-group;
              uses eem-set-ratelimit-group;
            }
            container routing {
              description
                "Routing event";
              leaf network {
                type union {
                  type inet:ipv4-prefix;
                  type ios-types:ipv6-prefix;
                }
              }
              leaf type {
                description
                  "A routing table entry is added, removed or modified";
                type enumeration {
                  enum add;
                  enum all;
                  enum modify;
                  enum remove;
                }
              }
              uses eem-set-maxrun-group;
              uses eem-set-ratelimit-group;
            }
          }
          container timer {
            description
              "Timer event";
            status deprecated;
            container absolute {
              description
                "Absolute timer event";
              status deprecated;
              leaf maxrun {
                description
                  "Maximum runtime of applet";
                status deprecated;
                type uint32 {
                  range "0..31536000";
                }
              }
              leaf name {
                description
                  "Timer name string";
                status deprecated;
                type string;
              }
              leaf ratelimit {
                description
                  "seconds[.milliseconds] value";
                status deprecated;
                type uint32 {
                  range "0..31536000";
                }
              }
              leaf time {
                description
                  "Time period for watchdog / countdown / absolute timer";
                status deprecated;
                type uint32 {
                  range "1..2085978494";
                }
              }
            }
            container countdown {
              description
                "Countdown timer event";
              status deprecated;
              leaf maxrun {
                description
                  "Maximum runtime of applet";
                status deprecated;
                type uint32 {
                  range "0..31536000";
                }
              }
              leaf name {
                description
                  "Timer name string";
                status deprecated;
                type string;
              }
              leaf ratelimit {
                description
                  "seconds[.milliseconds] value";
                status deprecated;
                type uint32 {
                  range "0..31536000";
                }
              }
              leaf time {
                description
                  "Time period for watchdog / countdown / absolute timer";
                status deprecated;
                type uint32 {
                  range "1..2085978494";
                }
              }
            }
            container cron {
              description
                "cron timer event";
              status deprecated;
              leaf maxrun {
                description
                  "Maximum runtime of applet";
                status deprecated;
                type uint32 {
                  range "0..31536000";
                }
              }
              leaf name {
                description
                  "Timer name string";
                status deprecated;
                type string;
              }
              leaf ratelimit {
                description
                  "seconds[.milliseconds] value";
                status deprecated;
                type uint32 {
                  range "0..31536000";
                }
              }
              leaf cron-entry {
                description
                  "Cron entry for cron timer";
                status deprecated;
                type string;
              }
            }
            container watchdog {
              description
                "Watchdog timer event";
              status deprecated;
              leaf maxrun {
                description
                  "Maximum runtime of applet";
                status deprecated;
                type uint32 {
                  range "0..31536000";
                }
              }
              leaf name {
                description
                  "Timer name string";
                status deprecated;
                type string;
              }
              leaf ratelimit {
                description
                  "seconds[.milliseconds] value";
                status deprecated;
                type uint32 {
                  range "0..31536000";
                }
              }
              leaf time {
                description
                  "Time period for watchdog / countdown / absolute timer";
                status deprecated;
                type uint32 {
                  range "1..2085978494";
                }
              }
            }
          }
          container snmp-notification {
            description
              "SNMP Notification Event";
            leaf oid {
              description
                "Object ID of data element";
              type string;
            }
            leaf oid-val {
              description
                "Comparison value";
              type string;
            }
            leaf op {
              description
                "Operator";
              type operator-type;
            }
            leaf src-ip-address {
              description
                "Source ip address";
              type union {
                type inet:ipv4-address;
                type inet:ipv6-address;
              }
            }
            leaf dest-ip-address {
              description
                "Destination ip address";
              type union {
                type inet:ipv4-address;
                type inet:ipv6-address;
              }
            }
          }
          container syslog {
            description
              "Syslog event";
            status deprecated;
            leaf pattern {
              description
                "Pattern match string for the entire message";
              status deprecated;
              type string;
            }
          }
          container track {
            description
              "Tracking object event";
            status deprecated;
            leaf track-object-number {
              description
                "Tracking object number";
              status deprecated;
              type uint16 {
                range "1..1000";
              }
            }
            leaf state {
              description
                "State of tracking object";
              status deprecated;
              when '../track-object-number';
              type enumeration {
                enum any;
                enum down;
                enum up;
              }
              default "any";
            }
            leaf maxrun {
              description
                "Maximum runtime of applet";
              status deprecated;
              type uint32 {
                range "0..31536000";
              }
            }
            leaf ratelimit {
              description
                "Limit trigger to once per given time period";
              status deprecated;
              type uint32 {
                range "0..31536000";
              }
            }
          }
          container none {
            description
              "Manually run policy event";
            status deprecated;
            presence "true";
            leaf default {
              status deprecated;
              description
                "Default action timer";
              type uint32;
            }
            leaf maxrun {
              description
                "Maximum runtime of applet";
              status deprecated;
              type uint32 {
                range "0..31536000";
              }
            }
            leaf ratelimit {
              description
                "seconds[.milliseconds] value";
              status deprecated;
              type uint32 {
                range "0..31536000";
              }
            }
            leaf sync {
              description
                "EEM policy execution sync or async";
              status deprecated;
              type enumeration {
                enum yes;
                enum no;
              }
            }
          }
          container resource {
            description
              "Resource event";
            leaf policy {
              description
                "Resource policy name string";
              type string;
            }
            uses eem-set-maxrun-group;
            uses eem-set-ratelimit-group;
          }
          container rpc {
            description
              "Remote Procedure Call event";
            presence "true";
            uses eem-default-group;
            uses eem-maxrun-group;
            uses eem-ratelimit-group;
          }
          container config {
            description
              "Configuration policy event";
            presence "true";
            uses eem-maxrun-group;
            uses eem-ratelimit-group;
          }
          container env {
            description
              "Environmental event";
            container severity {
              description
                "alarm severity";
              choice severty-level {
                container major {
                  description
                    "major environmental alarm";
                  presence "true";
                  uses eem-maxrun-group;
                  uses eem-ratelimit-group;
                }
                container minor {
                  description
                    "minor environmental alarm";
                  presence "true";
                  uses eem-maxrun-group;
                  uses eem-ratelimit-group;
                }
              }
            }
          }
          container oir {
            description
              "OIR event";
            presence "true";
            leaf event {
              description
                "OIR event";
              type enumeration {
                enum all;
                enum insert;
                enum removal;
              }
            }
            uses eem-maxrun-group;
          }
          container rf {
            description
              "event match string";
            leaf event {
              description
                "Event match string";
              type string;
            }
            uses eem-maxrun-group;
            uses eem-ratelimit-group;
          }
        }
        list action {
          description
            "Add or modify an action statement";
          ordered-by user;
          key "name";
          leaf name {
            description
              "Label";
            type string;
          }
          choice list-option {
            container cli-choice {
              description
                "Execute a CLI command";
              leaf command {
                description
                  "CLI command";
                type string;
              }
            }
            container regexp-option {
              description
                "regular expression match";
              leaf string-pattern {
                description
                  "regular expression pattern";
                type string;
              }
              leaf string-input {
                description
                  "input string";
                type string;
              }
              leaf string-match {
                description
                  "match variable";
                type string;
              }
              leaf string-submatch1 {
                description
                  "subsequent match variable";
                type string;
              }
              leaf string-submatch2 {
                description
                  "subsequent match variable";
                type string;
              }
              leaf string-submatch3 {
                description
                  "subsequent match variable";
                type string;
              }
            }
            container syslog-option {
              description
                "Log a syslog message";
              leaf facility {
                description
                  "Facility string";
                type string;
              }
              leaf msg {
                description
                  "Syslog message";
                type string;
              }
              leaf priority {
                description
                  "Priority of syslog message";
                type ios:logging-level-type;
              }
            }
          }
          container cli {
            description
              "Execute a CLI command";
            status deprecated;
            leaf command {
              description
                "CLI command";
              status deprecated;
              type string;
            }
          }
          container if {
            description
              "if conditional";
            leaf string-op-1 {
              type string;
            }
            leaf keyword {
              type operator-type;
            }
            leaf string-op-2 {
              type string;
            }
            leaf goto {
              description
                "goto label";
              type string;
            }
          }
          container info {
            description
              "Obtain system specific information";
            container type {
              description
                "Type of information to obtain";
              container snmp {
                description
                  "SNMP information";
                container var {
                  description
                    "Trap variable";
                  leaf variable-name {
                    type string;
                  }
                  leaf oid {
                    description
                      "SNMP object id";
                    type string;
                  }
                  leaf oid-type {
                    type enumeration {
                      enum counter;
                      enum gauge;
                      enum int;
                      enum ipv4;
                      enum octet;
                      enum string;
                      enum uint;
                    }
                  }
                  leaf oid-type-value {
                    type string;
                  }
                }
                container trap {
                  description
                    "SNMP trap";
                  leaf enterprise-oid {
                    description
                      "Enterprise oid";
                    type string;
                  }
                  leaf generic-trapnum {
                    description
                      "Generic trap number";
                    type uint32;
                  }
                  leaf specific-trapnum {
                    description
                      "Specific trap number";
                    type uint32;
                  }
                  leaf trap-oid {
                    description
                      "Trap oid";
                    type string;
                  }
                  leaf trap-var {
                    description
                      "Trap variable";
                    type string;
                  }
                }
              }
            }
          }
          leaf end {
            description
              "end conditional block";
            type empty;
          }
          container regexp {
            description
              "regular expression match";
            status deprecated;
            leaf string-pattern {
              status deprecated;
              type string;
            }
            leaf string-input {
              status deprecated;
              type string;
            }
            leaf string-match {
              status deprecated;
              type string;
            }
            leaf string-submatch1 {
              status deprecated;
              type string;
            }
            leaf string-submatch2 {
              status deprecated;
              type string;
            }
            leaf string-submatch3 {
              status deprecated;
              type string;
            }
          }
          container snmp-trap {
            description
              "Send an SNMP trap";
            presence "true";
            leaf intdata1 {
              description
                "SNMP integer data1";
              type int32;
            }
            leaf intdata2 {
              description
                "SNMP integer data2";
              type int32;
            }
            leaf strdata {
              description
                "SNMP trap string";
              type string;
            }
          }
          container string {
            description
              "string commands";
            leaf trim {
              description
                "trim characters from both ends of string";
              type string;
            }
          }
          container syslog {
            description
              "Log a syslog message";
            status deprecated;
            leaf facility {
              description
                "Facility string";
              status deprecated;
              type string;
            }
            leaf msg {
              description
                "Syslog message";
              status deprecated;
              type string;
            }
            leaf priority {
              description
                "Priority of syslog message";
              status deprecated;
              type ios:logging-level-type;
            }
          }
          leaf wait {
            description
              "Wait for a specified amount of time";
            type uint32 {
              range "1..31536000";
            }
          }
          leaf exit {
            description
              "Exit from applet run";
            type empty;
          }
          leaf reload {
            description
              "Reload system";
            type empty;
          }
        }
        leaf description {
          description
            "Add or modify an applet description";
          type string;
        }
        container trigger {
          description
            "Enter applet trigger configuration submode";
        }
      }
    }
  }

  augment "/ios:native/ios:event" {
    uses config-eem-grouping;
  }
}
