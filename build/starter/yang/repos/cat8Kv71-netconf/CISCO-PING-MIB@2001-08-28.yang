/*
 * Generated by confdc --mib2yang-std
 * Source: mgmt/dmi/model/mib/src/CISCO-PING-MIB.mib
 */
/*
 * This YANG module has been generated by smidump 0.5.0:
 *
 *      smidump -f yang CISCO-PING-MIB
 *
 * Do not edit. Edit the source file instead!
 */

module CISCO-PING-MIB {

  namespace "urn:ietf:params:xml:ns:yang:smiv2:CISCO-PING-MIB";
  prefix CISCO-PING-MIB;

  import CISCO-TC {
    prefix "cisco-tc";
  }

  import IF-MIB {
    prefix "if-mib";
  }

  import SNMPv2-TC {
    prefix "snmpv2-tc";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-snmp@cisco.com";

  description
   "Modified description of ciscoPingAddress object.";

  revision 2001-08-28 {
    description
     "Added VPN name to notifications";
  }

  revision 2001-05-14 {
    description
     "Add VrfName attribute to support VPN ping";
  }

  revision 1999-10-08 {
    description
     "";
  }

  revision 1994-11-11 {
    description
     "Redefined Ping completion trap.";
  }

  revision 1994-07-22 {
    description
     "Initial version of this MIB module.";
  }


  container CISCO-PING-MIB {
    config false;

    container ciscoPingTable {
      description
       "A table of ping request entries.";
      smiv2:oid "1.3.6.1.4.1.9.9.16.1.1";

      list ciscoPingEntry {
        key "ciscoPingSerialNumber";
        description
         "A ping request entry.
          
          A management station wishing to create an entry should
          first generate a pseudo-random serial number to be used
          as the index to this sparse table.  The station should
          then create the associated instance of the row status
          and row owner objects.  It must also, either in the same
          or in successive PDUs, create the associated instance of
          the protocol and address objects.  It should also modify
          the default values for the other configuration objects
          if the defaults are not appropriate.
          
          Once the appropriate instance of all the configuration
          objects have been created, either by an explicit SNMP
          set request or by default, the row status should be set
          to active to initiate the request.  Note that this entire
          procedure may be initiated via a single set request which
          specifies a row status of createAndGo as well as specifies
          valid values for the non-defaulted configuration objects.
          
          Once the ping sequence has been activated, it cannot be
          stopped -- it will run until the configured number of
          packets have been sent.
          
          Once the sequence completes, the management station should
          retrieve the values of the status objects of interest, and
          should then delete the entry.  In order to prevent old
          entries from clogging the table, entries will be aged out,
          but an entry will never be deleted within 5 minutes of
          completing.";
        smiv2:oid "1.3.6.1.4.1.9.9.16.1.1.1";

        leaf ciscoPingSerialNumber {
          type int32 {
            range "1..2147483647";
          }
          description
           "Object which specifies a unique entry in the
            ciscoPingTable.  A management station wishing
            to initiate a ping operation should use a
            pseudo-random value for this object when creating
            or modifying an instance of a ciscoPingEntry.
            The RowStatus semantics of the ciscoPingEntryStatus
            object will prevent access conflicts.";
          smiv2:max-access "not-accessible";
          smiv2:oid "1.3.6.1.4.1.9.9.16.1.1.1.1";
        }

        leaf ciscoPingProtocol {
          type cisco-tc:CiscoNetworkProtocol;
          description
           "The protocol to use.
            Once an instance of this object is created, its
            value can not be changed.";
          smiv2:max-access "read-write";
          smiv2:oid "1.3.6.1.4.1.9.9.16.1.1.1.2";
        }

        leaf ciscoPingAddress {
          type cisco-tc:CiscoNetworkAddress;
          description
           "The address of the device to be pinged.
            An instance of this object cannot be created until the
            associated instance of ciscoPingProtocol is created.";
          smiv2:max-access "read-write";
          smiv2:oid "1.3.6.1.4.1.9.9.16.1.1.1.3";
        }

        leaf ciscoPingPacketCount {
          type int32 {
            range "1..2147483647";
          }
          description
           "Specifies the number of ping packets to send to the target
            in this sequence.";
          smiv2:defval "5";
          smiv2:max-access "read-write";
          smiv2:oid "1.3.6.1.4.1.9.9.16.1.1.1.4";
        }

        leaf ciscoPingPacketSize {
          type int32;
          description
           "Specifies the size of ping packets to send to the target
            in this sequence.  The lower and upper boundaries of this
            object are protocol-dependent.
            An instance of this object cannot be modified unless the
            associated instance of ciscoPingProtocol has been created
            (so as to allow protocol-specific range checking on the
            new value).";
          smiv2:defval "100";
          smiv2:max-access "read-write";
          smiv2:oid "1.3.6.1.4.1.9.9.16.1.1.1.5";
        }

        leaf ciscoPingPacketTimeout {
          type int32 {
            range "0..3600000";
          }
          units "milliseconds";
          description
           "Specifies the amount of time to wait for a response to a
            transmitted packet before declaring the packet 'dropped.'";
          smiv2:defval "2000";
          smiv2:max-access "read-write";
          smiv2:oid "1.3.6.1.4.1.9.9.16.1.1.1.6";
        }

        leaf ciscoPingDelay {
          type int32 {
            range "0..3600000";
          }
          units "milliseconds";
          description
           "Specifies the minimum amount of time to wait before sending
            the next packet in a sequence after receiving a response or
            declaring a timeout for a previous packet.  The actual delay
            may be greater due to internal task scheduling.";
          smiv2:defval "0";
          smiv2:max-access "read-write";
          smiv2:oid "1.3.6.1.4.1.9.9.16.1.1.1.7";
        }

        leaf ciscoPingTrapOnCompletion {
          type boolean;
          description
           "Specifies whether or not a ciscoPingCompletion trap should
            be issued on completion of the sequence of pings.  If such a
            trap is desired, it is the responsibility of the management
            entity to ensure that the SNMP administrative model is
            configured in such a way as to allow the trap to be delivered.";
          smiv2:defval "false";
          smiv2:max-access "read-write";
          smiv2:oid "1.3.6.1.4.1.9.9.16.1.1.1.8";
        }

        leaf ciscoPingSentPackets {
          type yang:counter32;
          description
           "The number of ping packets that have been sent to the target
            in this sequence.";
          smiv2:max-access "read-only";
          smiv2:oid "1.3.6.1.4.1.9.9.16.1.1.1.9";
        }

        leaf ciscoPingReceivedPackets {
          type yang:counter32;
          description
           "The number of ping packets that have been received from the
            target in this sequence.";
          smiv2:max-access "read-only";
          smiv2:oid "1.3.6.1.4.1.9.9.16.1.1.1.10";
        }

        leaf ciscoPingMinRtt {
          type int32;
          units "milliseconds";
          description
           "The minimum round trip time of all the packets that have
            been sent in this sequence.
            
            This object will not be created until the first ping
            response in a sequence is received.";
          smiv2:max-access "read-only";
          smiv2:oid "1.3.6.1.4.1.9.9.16.1.1.1.11";
        }

        leaf ciscoPingAvgRtt {
          type int32;
          units "milliseconds";
          description
           "The average round trip time of all the packets that have
            been sent in this sequence.
            
            This object will not be created until the first ping
            response in a sequence is received.";
          smiv2:max-access "read-only";
          smiv2:oid "1.3.6.1.4.1.9.9.16.1.1.1.12";
        }

        leaf ciscoPingMaxRtt {
          type int32;
          units "milliseconds";
          description
           "The maximum round trip time of all the packets that have
            been sent in this sequence.
            
            This object will not be created until the first ping
            response in a sequence is received.";
          smiv2:max-access "read-only";
          smiv2:oid "1.3.6.1.4.1.9.9.16.1.1.1.13";
        }

        leaf ciscoPingCompleted {
          type boolean;
          description
           "Set to true when all the packets in this sequence have been
            either responded to or timed out.";
          smiv2:max-access "read-only";
          smiv2:oid "1.3.6.1.4.1.9.9.16.1.1.1.14";
        }

        leaf ciscoPingEntryOwner {
          type if-mib:OwnerString;
          description
           "The entity that configured this entry.";
          smiv2:max-access "read-write";
          smiv2:oid "1.3.6.1.4.1.9.9.16.1.1.1.15";
        }

        leaf ciscoPingEntryStatus {
          type snmpv2-tc:RowStatus;
          description
           "The status of this table entry.  Once the entry status is
            set to active, the associate entry cannot be modified until
            the sequence completes (ciscoPingCompleted is true).";
          smiv2:max-access "read-write";
          smiv2:oid "1.3.6.1.4.1.9.9.16.1.1.1.16";
        }

        leaf ciscoPingVrfName {
          type binary {
            length "0..32";
          }
          description
           "This field is used to specify the VPN name in 
            which the ping will be used. For regular ping this
            field should not be configured. The agent will use
            this field to identify the VPN routing Table for 
            this ping. This is the same ascii string used in 
            the CLI to refer to this VPN. ";
          smiv2:defval "";
          smiv2:max-access "read-write";
          smiv2:oid "1.3.6.1.4.1.9.9.16.1.1.1.17";
        }
      }
    }
  }

  notification ciscoPingCompletion {
    description
     "A ciscoPingCompleted trap is sent at the completion
      of a sequence of pings if such a trap was requested
      when the sequence was initiated.  In addition to the
      above listed objects (which are always present),
      the message will contain the following objects if 
      any responses were received:
              ciscoPingMinRtt
              ciscoPingAvgRtt
              ciscoPingMaxRtt
      It will also contain the following object if the ping
      is to a VPN address:
              ciscoPingVrfName";
    smiv2:oid "1.3.6.1.4.1.9.9.16.2.0.1";

    container object-1 {

      leaf ciscoPingSerialNumber {
        type leafref {
          path "/CISCO-PING-MIB:CISCO-PING-MIB/CISCO-PING-MIB:ciscoPingTable/CISCO-PING-MIB:ciscoPingEntry/CISCO-PING-MIB:ciscoPingSerialNumber";
        }
      }

      leaf ciscoPingCompleted {
        type leafref {
          path "/CISCO-PING-MIB:CISCO-PING-MIB/CISCO-PING-MIB:ciscoPingTable/CISCO-PING-MIB:ciscoPingEntry/CISCO-PING-MIB:ciscoPingCompleted";
        }
      }
    }

    container object-2 {

      leaf ciscoPingSerialNumber {
        type leafref {
          path "/CISCO-PING-MIB:CISCO-PING-MIB/CISCO-PING-MIB:ciscoPingTable/CISCO-PING-MIB:ciscoPingEntry/CISCO-PING-MIB:ciscoPingSerialNumber";
        }
      }

      leaf ciscoPingSentPackets {
        type leafref {
          path "/CISCO-PING-MIB:CISCO-PING-MIB/CISCO-PING-MIB:ciscoPingTable/CISCO-PING-MIB:ciscoPingEntry/CISCO-PING-MIB:ciscoPingSentPackets";
        }
      }
    }

    container object-3 {

      leaf ciscoPingSerialNumber {
        type leafref {
          path "/CISCO-PING-MIB:CISCO-PING-MIB/CISCO-PING-MIB:ciscoPingTable/CISCO-PING-MIB:ciscoPingEntry/CISCO-PING-MIB:ciscoPingSerialNumber";
        }
      }

      leaf ciscoPingReceivedPackets {
        type leafref {
          path "/CISCO-PING-MIB:CISCO-PING-MIB/CISCO-PING-MIB:ciscoPingTable/CISCO-PING-MIB:ciscoPingEntry/CISCO-PING-MIB:ciscoPingReceivedPackets";
        }
      }
    }
  }

  smiv2:alias "ciscoPingMIB" {
    smiv2:oid "1.3.6.1.4.1.9.9.16";
  }

  smiv2:alias "ciscoPingMIBObjects" {
    smiv2:oid "1.3.6.1.4.1.9.9.16.1";
  }

  smiv2:alias "ciscoPingMIBTrapPrefix" {
    smiv2:oid "1.3.6.1.4.1.9.9.16.2";
  }

  smiv2:alias "ciscoPingMIBTraps" {
    smiv2:oid "1.3.6.1.4.1.9.9.16.2.0";
  }

  smiv2:alias "ciscoPingMIBConformance" {
    smiv2:oid "1.3.6.1.4.1.9.9.16.3";
  }

  smiv2:alias "ciscoPingMIBCompliances" {
    smiv2:oid "1.3.6.1.4.1.9.9.16.3.1";
  }

  smiv2:alias "ciscoPingMIBGroups" {
    smiv2:oid "1.3.6.1.4.1.9.9.16.3.2";
  }

}
