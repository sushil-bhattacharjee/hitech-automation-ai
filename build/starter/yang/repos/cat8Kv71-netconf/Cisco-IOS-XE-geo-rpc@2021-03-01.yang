module Cisco-IOS-XE-geo-rpc {
  yang-version 1;
  namespace "http://cisco.com/ns/yang/Cisco-IOS-XE-geo-rpc";
  prefix geo-ios-xe-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2020 by Cisco Systems, Inc.
     All rights reserved.";

  revision 2021-03-01 {
    description
      "Initial revision";
    reference
      "1.0.0";
    cisco-semver:module-version "1.0.0";
  }

  typedef geo-database-type {
    type enumeration {
      enum update-use-file {
        value 0;
        description
          "Update Geo-Location Database via file";
      }
      enum revert-use-default {
        value 1;
        description
          "Revert to default Geo-Location Database file";
      }
    }
    description
      "Geo database actions";
  }

  grouping geo-database {
    description
      "Geo-Location Database actions for upgrading or reverting
       database files.";
    choice geo-database-type-by-choice {
      mandatory true;
      description
        "Geo-Location Database actions";
      case update-use-file {
        leaf update-file {
          type string {
            length "0..255";
            pattern '(flash:|bootflash:)[-A-Za-z_.0-9/]*[-A-Za-z_0-9]';
          }
          mandatory true;
          description
            "Specify the Geo-Location Database update file";
        }
      }
      case revert-use-default {
        leaf revert-default {
          type boolean;
          mandatory true;
          description
            "Revert to an older Geo-Location Database file";
        }
      }
    }
  }

  rpc geo-database {
    description
      "Geo-Location Database action RPC";
    input {
      uses geo-ios-xe-rpc:geo-database;
    }
  }
}
