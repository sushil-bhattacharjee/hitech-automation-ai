module Cisco-IOS-XE-fqdn {
  namespace "http://cisco.com/ns/yang/Cisco-IOS-XE-fqdn";
  prefix ios-fqdn;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE PnP Yang model.
     Copyright (c) 2020-2021 by Cisco Systems, Inc.
     All rights reserved.";

  revision 2020-11-01 {
    description
      "Added yang support for fqdn";
  }

  grouping config-fqdn-grouping {
    container fqdn {
      leaf ttl-timeout-factor {
        description
          "time-out factor for TTL";
        type union {
          type enumeration {
            enum infinite;
          }
          type uint16 {
            range "1..300";
          }
        }
        default "10";
      }
    }
  }

  augment "/ios:native" {
    uses config-fqdn-grouping;
  }
}
