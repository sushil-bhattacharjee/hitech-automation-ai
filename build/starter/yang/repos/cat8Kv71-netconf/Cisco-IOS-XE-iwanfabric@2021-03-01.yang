module Cisco-IOS-XE-iwanfabric {
  namespace "http://cisco.com/ns/yang/Cisco-IOS-XE-iwanfabric";
  prefix ios-iwanfabric;

  import cisco-semver {
    prefix cisco-semver;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native IWAN Fabric Yang model.
     Copyright (c) 2017 by Cisco Systems, Inc.
     All rights reserved.";

  revision 2021-03-01 {
    description
      "- Replaced tailf cli-diff-dependency";
    cisco-semver:module-version "1.0.1";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-04-28 {
    description
      "Initial revision";
  }

  grouping config-fabric-iwan-virtual-network-prefix-group {
    container prefix {
      description
        "prefix-group prefix configuration";
      container import {
        description
          "prefix import";
        container bgp {
          description
            "import from bgp as";
          list word {
            key "word";
            leaf word {
              description
                "Up to 19 character AS name";
              type string;
            }
            leaf route-map {
              description
                "Up to 19 characters route-map name";
              type string;
            }
          }
        }
        container eigrp {
          list word {
            key "word";
            leaf word {
              type string;
            }
            leaf route-map {
              description
                "Up to 19 characters route-map name";
              type string;
            }
          }
        }
        container isis {
          description
            "import from isis as";
          list word {
            key "word";
            leaf word {
              type string;
            }
            leaf route-map {
              description
                "Up to 19 characters route-map name";
              type string;
            }
          }
        }
        container lan-fabric {
          description
            "import from lan-fabric";
          leaf route-map {
            description
              "Up to 19 characters route-map name";
            type string;
          }
        }
        container ospf {
          description
            "import from ospf as";
          list word {
            key "word";
            leaf word {
              type string;
            }
            leaf route-map {
              description
                "Up to 19 characters route-map name";
              type string;
            }
          }
        }
        container rip {
          description
            "import from rip as";
          list word {
            key "word";
            leaf word {
              description
                "Up to 19 character AS name";
              type string;
            }
            leaf route-map {
              description
                "Up to 19 characters route-map name";
              type string;
            }
          }
        }
        container wan-fabric {
          description
            "import from wan-fabric";
          leaf route-map {
            description
              "Up to 19 characters route-map name";
            type string;
          }
        }
      }
      container ipv4 {
        description
          "IPv4 enterprise prefix-list";
        leaf prefix-list {
          description
            "Up to 19 character list name";
          type string;
        }
      }
      container ipv6 {
        description
          "IPv6 enterprise prefix-list";
        leaf prefix-list {
          description
            "Up to 19 character list name";
          type string;
        }
      }
    }
  }

  grouping config-iwanfabric-instance-grouping {
    container fabric-group {
      container fabric {
        description
          "Fabric Configuration submode";
        container auto {
          description
            "Fabric auto Configuration Commands";
          presence "true";
          container config-fabric-auto {
            container domain {
              description
                "domain Configuration Commands";
              container iwan-fabric {
                description
                  "iwan-fabric Configuration Commands";
                presence "true";
                container config-fabric-iwan {
                  container border {
                    description
                      "Enter the border type";
                    leaf self {
                      description
                        "self border type";
                      type empty;
                    }
                  }
                  container control-plane {
                    description
                      "Enter the PMCS configuration";
                    container destination-address {
                      list ipv4 {
                        key "ipv4";
                        leaf ipv4 {
                          type inet:ipv4-address;
                        }
                        container auth-key {
                          description
                            "Authentication key type";
                          list range {
                            key "range";
                            leaf range {
                              description
                                "Specify the auth-key type";
                              type uint16 {
                                range "1..65535";
                              }
                            }
                            leaf word {
                              description
                                "authentication key";
                              type string;
                            }
                          }
                        }
                      }
                    }
                    container source-address {
                      description
                        "Enter source interface";
                      leaf interface {
                        description
                          "Virtual ACR interface";
                        type string;
                      }
                    }
                  }
                  container device-role {
                    description
                      "Enter the device role";
                    leaf border {
                      description
                        "Border router device type";
                      type empty;
                    }
                    leaf edge {
                      description
                        "Edge device type";
                      type empty;
                    }
                    leaf nat-traversal-router {
                      description
                        "NAT traversal router device type";
                      type empty;
                    }
                    leaf transit-router {
                      description
                        "Transit router device type";
                      type empty;
                    }
                  }
                  leaf fabric-device-id {
                    description
                      "Specify the fabric-device-id value";
                    type uint16 {
                      range "1..65535";
                    }
                  }
                  container region {
                    description
                      "Enter the Region ID";
                    container id {
                      description
                        "Specify the Region ID";
                      list range {
                        key "range";
                        leaf range {
                          description
                            "Specify the Region ID value";
                          type uint16 {
                            range "1..65535";
                          }
                        }
                        leaf name {
                          description
                            "region Name";
                          type string;
                        }
                      }
                    }
                  }
                  leaf shutdown {
                    description
                      "shut the device";
                    type empty;
                  }
                  container site {
                    description
                      "Enter the site configuration";
                    container id {
                      description
                        "Specify the site ID";
                      list range {
                        key "range";
                        leaf range {
                          description
                            "Specify the site-id value";
                          type uint16 {
                            range "1..65535";
                          }
                        }
                        leaf name {
                          description
                            "Site Name";
                          type string;
                        }
                      }
                    }
                  }
                  container tenant {
                    description
                      "Tenant ID configuration";
                    container id {
                      description
                        "Specify the tenant id";
                      list range {
                        key "range";
                        leaf range {
                          description
                            "Specify the tenant-id value";
                          type uint32 {
                            range "1..4294967295";
                          }
                        }
                        leaf name {
                          description
                            "Tenant Name";
                          type string;
                        }
                      }
                    }
                  }
                  container virtual-network {
                    description
                      "Enter the instancevirtual network ID";
                    container name {
                      description
                        "Specify the virtual-network name";
                      list word {
                        key "word";
                        leaf word {
                          description
                            "virtual-network name";
                          type string;
                        }
                        list id {
                          description
                            "Specify the virtual-network ID";
                          key "range";
                          leaf range {
                            description
                              "Specify the virtual-network id value";
                            type uint32 {
                              range "0..16777214";
                            }
                          }
                          container config-fabric-iwan-virtual-network {
                            container enterprise-prefix {
                              description
                                "Enterprise prefix configuration";
                              container ipv4 {
                                description
                                  "IPv4 enterprise prefix-list";
                                leaf prefix-list {
                                  description
                                    "Up to 19 character list name";
                                  type string;
                                }
                              }
                              container ipv6 {
                                description
                                  "IPv6 enterprise prefix-list";
                                leaf prefix-list {
                                  description
                                    "Up to 19 character list name";
                                  type string;
                                }
                              }
                            }
                            container prefix-group {
                              description
                                "prefix group configuration";
                              list word {
                                key "word";
                                leaf word {
                                  description
                                    "Up to 19 character list name";
                                  type string;
                                }
                                list vrf {
                                  description
                                    "Specify the virtual routing instance name";
                                  key "word";
                                  leaf word {
                                    description
                                      "Up to 19 character list name";
                                    type string;
                                  }
                                  container config-fabric-iwan-virtual-network-prefix-group {
                                    uses config-fabric-iwan-virtual-network-prefix-group;
                                  }
                                }
                              }
                            }
                          }
                        }
                      }
                    }
                  }
                }
              }
            }
          }
        }
      }
    }
  }

  grouping config-iwanfabric-interface-grouping {
    container fabric-domain {
      description
        "Fabric-domain interface command";
      container iwan-fabric {
        list word {
          key "word";
          leaf word {
            description
              "Path name";
            type string;
          }
          leaf interface-id {
            description
              "Specify the interface-id value";
            type uint8 {
              range "1..255";
            }
          }
        }
      }
    }
  }

  augment "/ios:native" {
    uses config-iwanfabric-instance-grouping;
  }

  augment "/ios:native/ios:interface/ios:FastEthernet" {
    uses config-iwanfabric-interface-grouping;
  }

  augment "/ios:native/ios:interface/ios:GigabitEthernet" {
    uses config-iwanfabric-interface-grouping;
  }

  augment "/ios:native/ios:interface/ios:TwoGigabitEthernet" {
    uses config-iwanfabric-interface-grouping;
  }

  augment "/ios:native/ios:interface/ios:FiveGigabitEthernet" {
    uses config-iwanfabric-interface-grouping;
  }

  augment "/ios:native/ios:interface/ios:AppGigabitEthernet" {
    uses config-iwanfabric-interface-grouping;
  }

  augment "/ios:native/ios:interface/ios:TenGigabitEthernet" {
    uses config-iwanfabric-interface-grouping;
  }

  augment "/ios:native/ios:interface/ios:TwentyFiveGigE" {
    uses config-iwanfabric-interface-grouping;
  }

  augment "/ios:native/ios:interface/ios:FortyGigabitEthernet" {
    uses config-iwanfabric-interface-grouping;
  }

  augment "/ios:native/ios:interface/ios:HundredGigE" {
    uses config-iwanfabric-interface-grouping;
  }
}
