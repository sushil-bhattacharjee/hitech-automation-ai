/*
 * Generated by confdc --mib2yang-std
 * Source: mgmt/dmi/model/mib/src/CISCO-IETF-PW-ENET-MIB.mib
 */
/*
 * This YANG module has been generated by smidump 0.5.0:
 *
 *      smidump -f yang CISCO-IETF-PW-ENET-MIB
 *
 * Do not edit. Edit the source file instead!
 */

module CISCO-IETF-PW-ENET-MIB {

  namespace "urn:ietf:params:xml:ns:yang:smiv2:CISCO-IETF-PW-ENET-MIB";
  prefix CISCO-IETF-PW-ENET-MIB;

  import CISCO-IETF-PW-MIB {
    prefix "cisco-ietf";
  }

  import CISCO-IETF-PW-TC-MIB {
    prefix "cisco-ietf-pw";
  }

  import IF-MIB {
    prefix "if-mib";
  }

  import SNMPv2-TC {
    prefix "snmpv2-tc";
  }

  import ietf-yang-smiv2 {
    prefix "smiv2";
  }

  import ietf-yang-types {
    prefix "yang";
  }

  organization
   "IETF PWE3 Working group";

  contact
   "David Zelig 
    Postal: Corrigent Systems 
    126, Yigal Alon St. 
    Tel-Aviv, ISRAEL 
    Tel: +972-3-6945273 
    E-mail: davidz@corrigent.com 
    
    Thomas D. Nadeau 
    Postal: Cisco Systems, Inc. 
    250 Apollo Drive 
    Chelmsford, MA 01824 
    Tel:    +1-978-497-3051 
    Email:  tnadeau@cisco.com ";

  description
   "This MIB describes a model for managing Ethernet  
    point-to-point pseudo wire services over a Packet  
    Switched Network (PSN).";

  revision 2002-09-22 {
    description
     " Submited as draft-pwe3-enet-mib-00. 
      Changes from previous version: 
      1) Alignment with draft-pwe3-ethernet-encap-00.txt: 
         removing 'rangeVLAN' mode and the associated objects. 
      2) Relaxing requirement on value of pwVcEnetPortVlan in 
         port mode. ";
  }

  revision 2002-08-20 {
    description
     "Changes from previous version: 
      1) Add pwVcEnetVcIfIndex - Option for VC as ifIndex. 
      2) Change counters to 64 bits. 
      3) Add mode for adding/removing VLAN fields between PW and 
         CE bound interface. 
      4) Referencing draft-martini instead of draft-so. 
      5) Editorial changes for some description clauses. 
      6) MPLS PRI mapping table to be independent (not augmented). 
      7) Adapt descriptions and rules of use to  
         dratf-ietf-pwe3-Ethernet-encap-00. ";
  }

  revision 2002-02-03 {
    description
     "initial revision as -00 draft";
  }


  container CISCO-IETF-PW-ENET-MIB {
    config false;

    container cpwVcEnetTable {
      description
       "This table contains the index to the Ethernet tables  
        associated with this ETH VC, the VLAN configuration and  
        VLAN mode.";
      smiv2:oid "1.3.6.1.4.1.9.10.108.1.1";

      list cpwVcEnetEntry {
        key "cpwVcIndex cpwVcEnetPwVlan";
        description
         "This table is indexed by the same index that was created  
          for the associated entry in the PW VC Table in the 
          CISCO-IETF-PW-MIB.  The CpwVcIndex and the cpwVcEnetPwVlan 
          are used as indexes to allow multiple VLANs to exist on 
          the same PW. 
          
          An entry is created in this table by the agent for every  
          entry in the cpwVc table with a VcType of 'ethernetVLAN', 
          'ethernet' or 'ethernetVPLS'. Additional rows may be  
          created by the operator or the agent if multiple entries 
          are required for the same VC. 
          
          This table provides Ethernet port mapping and VLAN  
          configuration for each Ethernet VC.";
        smiv2:oid "1.3.6.1.4.1.9.10.108.1.1.1";

        leaf cpwVcIndex {
          type leafref {
            path "/cisco-ietf:CISCO-IETF-PW-MIB/cisco-ietf:cpwVcTable/cisco-ietf:cpwVcEntry/cisco-ietf:cpwVcIndex";
          }
        }

        leaf cpwVcEnetPwVlan {
          type cisco-ietf-pw:CpwVcVlanCfg;
          description
           "This Object defines the VLAN on the VC. The value of 4097 
            is used if the object is not applicable, for example when 
            mapping all packets from an Ethernet port to this VC. 
            The value of 4096 is used to indicate untagged frames (at  
            least from the PW point of view), for example if  
            cpwVcEnetVlanMode is equal 'removeVLAN' or when  
            cpwVcEnetVlanMode equal 'noChange' and cpwVcEnetPortVlan 
            is equal 4096.";
          smiv2:max-access "not-accessible";
          smiv2:oid "1.3.6.1.4.1.9.10.108.1.1.1.1";
        }

        leaf cpwVcEnetVlanMode {
          type enumeration {
            enum "other" {
              value "0";
            }
            enum "portBased" {
              value "1";
            }
            enum "noChange" {
              value "2";
            }
            enum "changeVlan" {
              value "3";
            }
            enum "addVlan" {
              value "4";
            }
            enum "removeVlan" {
              value "5";
            }
          }
          description
           "Indicate the mode of VLAN handling between the port  
            associated to the VC and the VC encapsulation itself. 
            
            - 'other' indicate operation that is not defined by 
              this MIB. 
            
            - 'portBased' indicates that the forwarder will forward 
              packets between the port and the PW independent of their 
              structure. 
            
            - 'noChange' indicates that the VC contains the original 
               user VLAN, as specified in cpwVcEnetPortVlan. 
            
            - 'changeVlan' indicates that the VLAN field on the VC  
              may be different than the VLAN field on the user's  
              port. 
            
            - 'removeVlan' indicates that the encapsulation on the  
              VC does not include the original VLAN field. Note  
              that PRI bits transparency is lost in this case. 
            
            - 'addVlan' indicate that a VLAN field will be added 
              on the PSN bound direction. cpwVcEnetPwVlan indicate 
              the value that will be added.  
            
            - 'removeVlan', 'addVlan' and 'changeVlan' implementation 
              is not required. ";
          smiv2:defval "noChange";
          smiv2:max-access "read-write";
          smiv2:oid "1.3.6.1.4.1.9.10.108.1.1.1.2";
        }

        leaf cpwVcEnetPortVlan {
          type cisco-ietf-pw:CpwVcVlanCfg;
          description
           "This object define the VLAN value on the physical port (or  
            VPLS virtual port) if a change is required to the VLAN value 
            between the VC and the physical/virtual port. 
            
            The value of this object can be ignored if the whole traffic  
            from the port is forwarded to one VC independent of the  
            tagging on the port, but it is RECOMENDED that the value in 
            this case will be '4097' indicating not relevant. 
            
            It MUST be equal to cpwVcEnetPwVlan if 'noChange' mode 
            is used. 
            
            The value 4096 indicate that no VLAN (i.e. untagged  
            frames) on the port are associated to this VC. This  
            allows the same behaviors as assigning 'Default VLAN'  
            to un-tagged frames. ";
          smiv2:defval "4097";
          smiv2:max-access "read-write";
          smiv2:oid "1.3.6.1.4.1.9.10.108.1.1.1.3";
        }

        leaf cpwVcEnetVcIfIndex {
          type if-mib:InterfaceIndexOrZero;
          description
           "It is sometimes convenient to model the VC PW as a  
            virtual interface in the ifTable. In these cases this  
            object hold the value of the ifIndex in the ifTable  
            representing this VC PW. A value of zero indicate no such  
            association or association is not yet known.";
          smiv2:max-access "read-write";
          smiv2:oid "1.3.6.1.4.1.9.10.108.1.1.1.4";
        }

        leaf cpwVcEnetPortIfIndex {
          type if-mib:InterfaceIndexOrZero;
          description
           "This object is used to specify the ifIndex of the ETHERNET 
            port associated with this VC for point-to-point Ethernet  
            service, or the ifIndex of the virtual interface of the VPLS  
            instance associated with the PW if the service is VPLS. Two  
            rows in this table can point to the same ifIndex only if: 
            
            1) It is required to support multiple COS on a MPLS PSN  
               for the same service (i.e.: a combination of ports and  
               VLANs) by the use of multiple VC, each with a different 
               COS. 
            
            2) There is no overlap of VLAN values specified in  
               cpwVcEnetPortVlan that are associated with this port. 
            
            A value of zero indicate that association to an ifIndex is 
            not yet known.";
          smiv2:max-access "read-write";
          smiv2:oid "1.3.6.1.4.1.9.10.108.1.1.1.5";
        }

        leaf cpwVcEnetRowStatus {
          type snmpv2-tc:RowStatus;
          description
           "Enable creating, deleting and modifying this row.";
          smiv2:max-access "read-write";
          smiv2:oid "1.3.6.1.4.1.9.10.108.1.1.1.6";
        }

        leaf cpwVcEnetStorageType {
          type snmpv2-tc:StorageType;
          description
           "Indicates the storage type of this row.";
          smiv2:max-access "read-write";
          smiv2:oid "1.3.6.1.4.1.9.10.108.1.1.1.7";
        }
      }
    }

    container cpwVcEnetMplsPriMappingTable {
      description
       "This table may be used for MPLS PSNs if there is a need  
        to hold multiple VC, each with different COS, for the same 
        user service (port + PW VLAN). Such a need may arise if the 
        MPLS network is capable of L-LSP or E-LSP without multiple 
        COS capabilities.  Each row is indexed by the cpwVcIndex  
        and indicate the PRI bits on the packet recieved from the  
        user port (or VPLS virtual port) that are 
        classified to this VC. Note that the EXP bit value of the VC 
        is configured in the CISCO-IETF-PW-MPLS-MIB.";
      smiv2:oid "1.3.6.1.4.1.9.10.108.1.2";

      list cpwVcEnetMplsPriMappingTableEntry {
        key "cpwVcIndex";
        description
         "Each entry is created if special classification based on  
          the PRI bits is required for this VC.";
        smiv2:oid "1.3.6.1.4.1.9.10.108.1.2.1";

        leaf cpwVcIndex {
          type leafref {
            path "/cisco-ietf:CISCO-IETF-PW-MIB/cisco-ietf:cpwVcTable/cisco-ietf:cpwVcEntry/cisco-ietf:cpwVcIndex";
          }
        }

        leaf cpwVcEnetMplsPriMapping {
          type bits {
            bit pri000 {
              position "0";
            }
            bit pri001 {
              position "1";
            }
            bit pri010 {
              position "2";
            }
            bit pri011 {
              position "3";
            }
            bit pri100 {
              position "4";
            }
            bit pri101 {
              position "5";
            }
            bit pri110 {
              position "6";
            }
            bit pri111 {
              position "7";
            }
            bit untagged {
              position "8";
            }
          }
          description
           "This object defines the groups of user PRI mapped into 
            this VC. Each bit set indicates that this user priority  
            is assigned to this VC. 
            
            The value 'untagged' is used to indicate that untagged  
            frames are also associated to this VC. 
            
            This object allow the use of different PSN COS based on  
            user marking of PRI bits in MPLS PSN with L-LSP or  
            E-LSP without multiple COS support. In all other cases,  
            the default value MUST be used. 
            
            It is REQUIRED that there is no overlap on this object  
            between rows serving the same service (port+ PW VLAN). 
            
            In case of missing BIT configuration between rows to  
            the same service, incoming packets with PRI marking not  
            configured should be handled by the VC with the lowest  
            COS. ";
          reference
           "See appendix A of <draft-ietf-pwe3i-ethernet-encap> 
            for mapping rules of the PRI bits to PSN COS.";
          smiv2:max-access "read-write";
          smiv2:oid "1.3.6.1.4.1.9.10.108.1.2.1.1";
        }

        leaf cpwVcEnetMplsPriMappingRowStatus {
          type snmpv2-tc:RowStatus;
          description
           "Enable creating, deleting and modifying this row.";
          smiv2:max-access "read-write";
          smiv2:oid "1.3.6.1.4.1.9.10.108.1.2.1.2";
        }

        leaf cpwVcEnetMplsPriMappingStorageType {
          type snmpv2-tc:StorageType;
          description
           "Indicates the storage type of this row.";
          smiv2:max-access "read-write";
          smiv2:oid "1.3.6.1.4.1.9.10.108.1.2.1.3";
        }
      }
    }

    container cpwVcEnetStatsTable {
      description
       "This table contains statistical counters specific for  
        Ethernet PW.";
      smiv2:oid "1.3.6.1.4.1.9.10.108.1.3";

      list cpwVcEnetStatsEntry {
        key "cpwVcIndex";
        description
         "Each entry represents the statistics gathered for the  
          VC carrying the Ethernet packets since this VC was  
          first created in the cpwVcEnetTable.";
        smiv2:oid "1.3.6.1.4.1.9.10.108.1.3.1";

        leaf cpwVcIndex {
          type leafref {
            path "/cisco-ietf:CISCO-IETF-PW-MIB/cisco-ietf:cpwVcTable/cisco-ietf:cpwVcEntry/cisco-ietf:cpwVcIndex";
          }
        }

        leaf cpwVcEnetStatsIllegalVlan {
          type yang:counter64;
          description
           "The number of packets received (from the PSN) on this VC with  
            an illegal VLAN field, missing VLAN field that was expected, or  
            A VLAN field when it was not expected. This counter is not  
            relevant if the VC type is 'ethernet' (i.e. raw mode), and  
            should be set to 0 by the agent to indicate this.";
          smiv2:max-access "read-only";
          smiv2:oid "1.3.6.1.4.1.9.10.108.1.3.1.1";
        }

        leaf cpwVcEnetStatsIllegalLength {
          type yang:counter64;
          description
           "The number of packets that were received with an illegal  
            Ethernet packet length on this VC. An illegal length is defined 
            as being greater than the value in the advertised maximum MTU  
            supported, or shorter than the allowed Ethernet packet size.";
          smiv2:max-access "read-only";
          smiv2:oid "1.3.6.1.4.1.9.10.108.1.3.1.2";
        }
      }
    }
  }

  smiv2:alias "cpwVcEnetMIB" {
    smiv2:oid "1.3.6.1.4.1.9.10.108";
  }

  smiv2:alias "cpwVcEnetNotifications" {
    smiv2:oid "1.3.6.1.4.1.9.10.108.0";
  }

  smiv2:alias "cpwVcEnetObjects" {
    smiv2:oid "1.3.6.1.4.1.9.10.108.1";
  }

  smiv2:alias "cpwVcEnetConformance" {
    smiv2:oid "1.3.6.1.4.1.9.10.108.2";
  }

  smiv2:alias "cpwVcEnetGroups" {
    smiv2:oid "1.3.6.1.4.1.9.10.108.2.1";
  }

  smiv2:alias "cpwVcEnetCompliances" {
    smiv2:oid "1.3.6.1.4.1.9.10.108.2.2";
  }

}
