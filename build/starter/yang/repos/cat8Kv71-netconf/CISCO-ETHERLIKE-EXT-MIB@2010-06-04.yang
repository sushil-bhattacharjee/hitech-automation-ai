/*
 * Generated by confdc --mib2yang-std
 * Source: mgmt/dmi/model/mib/src/CISCO-ETHERLIKE-EXT-MIB.mib
 */
/*
 * This YANG module has been generated by smidump 0.5.0:
 *
 *      smidump -f yang CISCO-ETHERLIKE-EXT-MIB
 *
 * Do not edit. Edit the source file instead!
 */

module CISCO-ETHERLIKE-EXT-MIB {

  namespace "urn:ietf:params:xml:ns:yang:smiv2:CISCO-ETHERLIKE-EXT-MIB";
  prefix CISCO-ETHERLIKE-EXT-MIB;

  import EtherLike-MIB {
    prefix "etherlike-mib";
  }

  import IF-MIB {
    prefix "if-mib";
  }

  import ietf-yang-smiv2 {
    prefix "smiv2";
  }

  organization
   "Cisco Systems, Inc.";

  contact
   "Cisco Systems
    Customer Service
    
    Postal: 170 W Tasman Drive
    San Jose, CA 95134
    USA
    
    Tel: +1 800 553-NETS
    
    E-mail: cs-lan-switch-snmp@cisco.com";

  description
   "The MIB module to describe generic objects for
    ethernet-like network interfaces. 
    
    This MIB provides ethernet-like network interfaces 
    information that are either excluded by EtherLike-MIB 
    or specific to Cisco products.";

  revision 2010-06-04 {
    description
     "Added a new table ceeSubInterfaceTable under new OID subtree
      ceeSubIf.
      
      Added a new group ciscoEtherExtSubIfGroup.
      
      Added a new Compliance ceeEtherExtMIBComplianceR01, which
      deprecates ceeEtherExtMIBCompliance.";
  }

  revision 2008-10-15 {
    description
     "Updated ceeDot3PauseExtAdminMode DESCRIPTION with
      correct dot3PauseOperMode values.";
  }

  revision 2008-01-09 {
    description
     "Initial version of this MIB module.";
  }


  container CISCO-ETHERLIKE-EXT-MIB {
    config false;

    container ceeDot3PauseExtTable {
      description
       "A list of additional descriptive and status
        information about the MAC Control PAUSE 
        function on the ethernet-like interfaces 
        attached to a particular system, in extension to
        dot3PauseTable in EtherLike-MIB. There will be 
        one row in this table for each ethernet-like 
        interface in the system which supports the MAC 
        Control PAUSE function.";
      smiv2:oid "1.3.6.1.4.1.9.9.645.1.1.1";

      list ceeDot3PauseExtEntry {
        key "dot3StatsIndex";
        description
         "An entry in the table, containing additional
          information about the MAC Control PAUSE function 
          on a single ethernet-like interface, in extension 
          to dot3PauseEntry in Etherlike-MIB.";
        smiv2:oid "1.3.6.1.4.1.9.9.645.1.1.1.1";

        leaf dot3StatsIndex {
          type leafref {
            path "/etherlike-mib:EtherLike-MIB/etherlike-mib:dot3StatsTable/etherlike-mib:dot3StatsEntry/etherlike-mib:dot3StatsIndex";
          }
        }

        leaf ceeDot3PauseExtAdminMode {
          type bits {
            bit txDesired {
              position "0";
            }
            bit rxDesired {
              position "1";
            }
          }
          description
           "Indicates preference to send or process pause
            frames on this interface.
            txDesired(0)  -  indicates preference to send pause 
                             frames, but autonegotiates flow 
                             control. This bit can only be 
                             turned on when the corresponding 
                             instance of dot3PauseAdminMode 
                             has the value of 'enabledXmit' or 
                             'enabledXmitAndRcv'.
            rxDesired(1)  -  indicates preference to process 
                             pause frames, but autonegotiates 
                             flow control. This bit can only be 
                             turned on when the corresponding 
                             instance of dot3PauseAdminMode 
                             has the value of 'enabledRcv' or 
                             'enabledXmitAndRcv'.";
          smiv2:max-access "read-write";
          smiv2:oid "1.3.6.1.4.1.9.9.645.1.1.1.1.1";
        }

        leaf ceeDot3PauseExtOperMode {
          type bits {
            bit txDisagree {
              position "0";
            }
            bit rxDisagree {
              position "1";
            }
            bit txDesired {
              position "2";
            }
            bit rxDesired {
              position "3";
            }
          }
          description
           "Provides additional information about the flow
            control operational status on this interface.
            txDisagree(0) - the transmit pause function on 
                            this interface is disabled due to 
                            disagreement from the far end on 
                            negotiation.
            rxDisagree(1) - the receive pause function on  
                            this interface is disabled due to 
                            disagreement from the far end on 
                            negotiation.
            txDesired(2)  - the transmit pause function on 
                            this interface is desired.
            rxDesired(3)  - the receive pause function on  
                            this interface is desired.";
          smiv2:max-access "read-only";
          smiv2:oid "1.3.6.1.4.1.9.9.645.1.1.1.1.2";
        }
      }
    }

    container ceeSubInterfaceTable {
      description
       "This table provides the subinterface related information
        associated to the Ethernet-like interfaces.
        
        The subinterface is a division of one physical interface into
        multiple logical interfaces. As an example of what a typical
        subinterface setup might look like on a device, a single
        Ethernet port such as GigabitEthernet0/0 would be subdivided
        into Gi0/0.1, Gi0/0.2, Gi0/0.3 and so on, each one performing as
        if it were a separate interface.";
      smiv2:oid "1.3.6.1.4.1.9.9.645.1.2.1";

      list ceeSubInterfaceEntry {
        key "ifIndex";
        description
         "This table contains a row for each Ethernet-like interface
          by it's ifTable ifIndex in the system, which supports the
          sub-interface.
          
          An entry is created by an agent, when it detects a
          Ethernet-like interface is created in ifTable and it 
          can support sub-interface.
          
          An entry is deleted by an agent, when the ifTable entry
          associated to the Ethernet-like interface is deleted.
          Typically, when the card is removed from the device.";
        smiv2:oid "1.3.6.1.4.1.9.9.645.1.2.1.1";

        leaf ifIndex {
          type leafref {
            path "/if-mib:IF-MIB/if-mib:ifTable/if-mib:ifEntry/if-mib:ifIndex";
          }
        }

        leaf ceeSubInterfaceCount {
          type uint32 {
            range "0..4294967295";
          }
          units "subifs";
          description
           "This object represents the number of subinterfaces
            created on a Ethernet-like interface.";
          smiv2:max-access "read-only";
          smiv2:oid "1.3.6.1.4.1.9.9.645.1.2.1.1.1";
        }
      }
    }
  }

  smiv2:alias "ciscoEtherExtMIB" {
    smiv2:oid "1.3.6.1.4.1.9.9.645";
  }

  smiv2:alias "ciscoEtherExtMIBNotifs" {
    smiv2:oid "1.3.6.1.4.1.9.9.645.0";
  }

  smiv2:alias "ciscoEtherExtMIBObjects" {
    smiv2:oid "1.3.6.1.4.1.9.9.645.1";
  }

  smiv2:alias "ceeDot3PauseExt" {
    smiv2:oid "1.3.6.1.4.1.9.9.645.1.1";
  }

  smiv2:alias "ceeSubIf" {
    smiv2:oid "1.3.6.1.4.1.9.9.645.1.2";
  }

  smiv2:alias "ciscoEtherExtMIBConform" {
    smiv2:oid "1.3.6.1.4.1.9.9.645.2";
  }

  smiv2:alias "ceeEtherExtMIBCompliances" {
    smiv2:oid "1.3.6.1.4.1.9.9.645.2.1";
  }

  smiv2:alias "ceeEtherExtMIBGroups" {
    smiv2:oid "1.3.6.1.4.1.9.9.645.2.2";
  }

}
