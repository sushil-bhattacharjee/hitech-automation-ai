module Cisco-IOS-XE-cef {
  namespace "http://cisco.com/ns/yang/Cisco-IOS-XE-cef";
  prefix ios-cef;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Cisco Express Forwarding (CEF) Yang model.
     Copyright (c) 2016-2017, 2019 by Cisco Systems, Inc.
     All rights reserved.";

  revision 2019-11-01 {
    description
      "- Added obsolete/deprecated status for child node when parent was
         already obsolete/deprecated";
    cisco-semver:module-version "2.0.0";
  }
  revision 2019-07-01 {
    description
      "Establish semantic version baseline";
    cisco-semver:module-version "1.0.0";
  }
  revision 2018-11-07 {
    description
      "Cleanup spelling errors in description statements";
  }
  revision 2017-05-19 {
    description
      "fix ip cef ip cef load-sharing algorithm include-ports configurations";
  }
  revision 2017-03-01 {
    description
      "Completion of cef table and ip cef configurations";
  }
  revision 2017-02-07 {
    description
      "Initial revision";
  }

  typedef fixed-id {
    description
      "<1-FFFFFFFF>  Fixed ID";
    type string {
      pattern '[0-9a-fA-F]{1,8}';
    }
  }

  grouping config-cef-get-fixed-id-grouping {
    leaf fixed-id {
      description
        "Fixed ID";
      type fixed-id;
    }
  }

  grouping config-af-cef-ldshr-alg-incl-ports-grouping {
    container include-ports {
      description
        "Algorithm that includes layer 4 ports";
      presence "true";
      container destination {
        presence "true";
        description
          "Use destination port in hash function";
        uses config-cef-get-fixed-id-grouping;
      }
      container source {
        description
          "Use source port in hash function";
        presence "true";
        container destination {
          description
            "Use source and destination ports in hash function";
          presence "true";
          container gtp {
            presence "true";
            description
              "Use GTP te-id as source and destination ports in hash function";
            uses config-cef-get-fixed-id-grouping;
          }
          uses config-cef-get-fixed-id-grouping;
        }
        uses config-cef-get-fixed-id-grouping;
      }
    }
  }

  feature asr1k-dpi {
    description
      "asr1k deep packet inspection";
  }

  grouping config-af-cef-ldshr-alg-dpi-grouping {
    container dpi {
      description
        "Deep Packet Inspection";
      if-feature "asr1k-dpi";
      leaf dpi {
        description
          "select-all";
        type empty;
      }
      leaf l2vpn-mac {
        description
          "l2vpn-mac";
        type empty;
      }
      leaf tunnel-gre {
        description
          "tunnel-gre";
        type empty;
      }
      leaf tunnel-ipinip {
        description
          "tunnel-ipinip";
        type empty;
      }
      leaf tunnel-ipsec {
        description
          "tunnel-ipsec";
        type empty;
      }
      leaf tunnel-l2tp {
        description
          "tunnel-l2tp";
        type empty;
      }
      leaf tunnel-vxlan {
        description
          "tunnel-vxlan";
        type empty;
      }
      uses config-cef-get-fixed-id-grouping;
    }
  }

  grouping config-af-cef-ldshr-alg-tun-grouping {
    container tunnel {
      description
        "Algorithm for use in tunnel only environments";
      leaf tunnel {
        type empty;
      }
      uses config-cef-get-fixed-id-grouping;
    }
  }

  grouping config-af-cef-ldshr-alg-uni-grouping {
    container universal {
      description
        "Algorithm for use in most environments";
      leaf universal {
        type empty;
      }
      uses config-cef-get-fixed-id-grouping;
    }
  }

  grouping config-af-cef-ldshr-alg-orig-grouping {
    container original {
      description
        "Original algorithm";
      leaf original {
        type empty;
      }
    }
  }

  grouping config-af-cef-load-sharing-key-ctrl-type-outer-port-grouping {
    choice outer-port {
      leaf ignore-outer-port {
        type empty;
      }
      leaf outer-dst-port {
        type empty;
      }
      leaf outer-src-dst-port {
        type empty;
      }
      leaf outer-src-port {
        type empty;
      }
    }
  }

  grouping config-af-cef-load-sharing-key-ctrl-type-outer-ip-grouping {
    choice outer-ip {
      status obsolete;
      leaf outer-dst-ip {
        type empty;
      }
      leaf outer-src-dst-ip {
        type empty;
      }
      leaf outer-src-ip {
        type empty;
      }
    }
  }

  grouping config-af-cef-load-sharing-key-ctrl-type-def-grouping {
    container default {
      description
        "Configure default hash fields";
      uses config-af-cef-load-sharing-key-ctrl-type-outer-ip-grouping;
      uses config-af-cef-load-sharing-key-ctrl-type-outer-port-grouping;
    }
  }

  grouping config-af-cef-load-sharing-key-ctrl-type-l2vpn-mac-grouping {
    container l2vpn-mac {
      description
        "Configure L2VPN-MAC type fields";
    }
  }

  grouping config-af-cef-load-sharing-key-ctrl-type-tun-gre-grouping {
    container tunnel-gre {
      description
        "Configure GRE type fields";
    }
  }

  grouping config-af-cef-load-sharing-key-ctrl-type-tun-ipinip-grouping {
    container tunnel-ipinip {
      description
        "Configure IPINIP type fields";
    }
  }

  grouping config-af-cef-load-sharing-key-ctrl-type-tun-ipsec-grouping {
    container tunnel-ipsec {
      description
        "Configure IPSEC type fields";
    }
  }

  grouping config-af-cef-load-sharing-key-ctrl-type-tun-l2tp-grouping {
    container tunnel-l2tp {
      description
        "Configure L2TP type fields";
    }
  }

  grouping config-af-cef-load-sharing-key-ctrl-type-tun-vxlan-grouping {
    container tunnel-vxlan {
      description
        "Configure VXLAN type fields";
    }
  }

  grouping config-af-cef-load-sharing-key-ctrl-grouping {
    container dpi {
      description
        "Deep Packet Inspection";
      uses config-af-cef-load-sharing-key-ctrl-type-def-grouping;
      uses config-af-cef-load-sharing-key-ctrl-type-l2vpn-mac-grouping;
      uses config-af-cef-load-sharing-key-ctrl-type-tun-gre-grouping;
      uses config-af-cef-load-sharing-key-ctrl-type-tun-ipinip-grouping;
      uses config-af-cef-load-sharing-key-ctrl-type-tun-ipsec-grouping;
      uses config-af-cef-load-sharing-key-ctrl-type-tun-l2tp-grouping;
      uses config-af-cef-load-sharing-key-ctrl-type-tun-vxlan-grouping;
    }
  }

  grouping config-v4-cef-load-sharing-grouping {
    container load-sharing {
      description
        "Load sharing";
      container algorithm {
        description
          "Per-destination load sharing algorithm selection";
        uses config-af-cef-ldshr-alg-uni-grouping;
        uses config-af-cef-ldshr-alg-tun-grouping;
        uses config-af-cef-ldshr-alg-orig-grouping;
        uses config-af-cef-ldshr-alg-incl-ports-grouping;
      }
      container key-control {
        description
          "Configure algorithm control values";
      }
    }
  }

  grouping config-v6-cef-load-sharing-grouping {
    container load-sharing {
      description
        "Load sharing";
      container algorithm {
        description
          "Per-destination load sharing algorithm selection";
        uses config-af-cef-ldshr-alg-tun-grouping;
        uses config-af-cef-ldshr-alg-uni-grouping;
        uses config-af-cef-ldshr-alg-orig-grouping;
        uses config-af-cef-ldshr-alg-incl-ports-grouping;
      }
      container key-control {
        description
          "Configure algorithm control values";
      }
    }
  }

  grouping config-af-cef-trfc-stats-grouping {
    container traffic-statistics {
      description
        "Enable collection of traffic statistics";
      leaf load-interval {
        description
          "Specify interval for load calculation";
        type uint16 {
          range "30..600";
        }
      }
      leaf update-rate {
        description
          "Specify update rate for non-recursive prefix stats";
        type uint16 {
          range "0..65535";
        }
      }
    }
  }

  grouping config-af-cef-acnt-opt-grouping {
    container accounting {
      description
        "Enable CEF accounting";
      leaf per-prefix {
        description
          "Enable per prefix accounting";
        type empty;
      }
      leaf non-recursive {
        description
          "Enable accounting for traffic through non-recursive prefixes";
        type empty;
      }
      leaf prefix-length {
        description
          "Enable prefix length accounting";
        type empty;
      }
      leaf load-balance-hash {
        description
          "Enable load balance hash accounting";
        type empty;
      }
    }
  }

  grouping config-af-cef-optimization-opt-grouping {
    container optimize {
      description
        "Optimizations";
      container neighbor {
        description
          "Optimizations for directly connected neighbors";
        leaf resolution {
          description
            "Trigger layer 2 address resolution directly from CEF";
          type empty;
        }
      }
    }
  }

  grouping config-af-cef-dist-grouping {
    leaf distributed {
      description
        "Distributed Cisco Express Forwarding";
      type empty;
    }
  }

  grouping config-af-cef-grouping {
    uses config-af-cef-acnt-opt-grouping;
    uses config-af-cef-dist-grouping;
    uses config-af-cef-optimization-opt-grouping;
    uses config-af-cef-trfc-stats-grouping;
  }

  grouping config-ip-cef-grouping {
    description
      "Cisco Express Forwarding for IPv4";
    uses config-af-cef-grouping;
    uses config-v4-cef-load-sharing-grouping;
  }

  grouping config-ipv6-cef-grouping {
    description
      "Cisco Express Forwarding for IPv6";
    uses config-af-cef-grouping;
    uses config-v6-cef-load-sharing-grouping;
  }

  grouping config-cef-tbl-cnst-chk-opt-types-scan-opt-grouping {
    container scan-opt {
      leaf count {
        description
          "Maximum number of prefixes to check per scan";
        type uint16 {
          range "2..10000";
        }
      }
      leaf period {
        description
          "Period between scans";
        type uint16 {
          range "30..3600";
        }
      }
    }
  }

  grouping config-cef-tbl-cnst-chk-opt-v4-types-grouping {
    container scan-ios-rib {
      description
        "Passive scan that checks RP tables against RIB";
      uses config-cef-tbl-cnst-chk-opt-types-scan-opt-grouping;
    }
    container scan-rib-ios {
      description
        "Passive scan that checks RIB against RP tables";
      uses config-cef-tbl-cnst-chk-opt-types-scan-opt-grouping;
    }
    container scan-lc-rp {
      description
        "Passive scan that checks LC tables against RP tables";
      uses config-cef-tbl-cnst-chk-opt-types-scan-opt-grouping;
    }
    container scan-rp-lc {
      description
        "Passive scan that checks RP tables against LC tables";
      uses config-cef-tbl-cnst-chk-opt-types-scan-opt-grouping;
    }
    leaf lc-detect {
      description
        "Linecard detects missing prefix. Confirmed by RP";
      type empty;
    }
  }

  grouping config-cef-tbl-cnst-chk-opt-v6-types-grouping {
    container scan-ios-rib {
      description
        "Passive scan that checks RP tables against RIB";
      uses config-cef-tbl-cnst-chk-opt-types-scan-opt-grouping;
    }
    container scan-lc-rp {
      description
        "Passive scan that checks LC tables against RP tables";
      uses config-cef-tbl-cnst-chk-opt-types-scan-opt-grouping;
    }
    container scan-rp-lc {
      description
        "Passive scan that checks RP tables against LC tables";
      uses config-cef-tbl-cnst-chk-opt-types-scan-opt-grouping;
    }
    leaf lc-detect {
      description
        "Linecard detects missing prefix. Confirmed by RP";
      type empty;
    }
  }

  grouping config-cef-tbl-cnst-chk-opt-v4-common-grouping {
    container auto-repair {
      description
        "Control auto-repair function";
      leaf delay {
        description
          "Delay in seconds";
        type uint16 {
          range "10..300";
        }
      }
      leaf holddown {
        description
          "Delay in seconds";
        type uint16 {
          range "300..3000";
        }
      }
    }
    container type {
      description
        "Type of consistency check to configure";
      uses config-cef-tbl-cnst-chk-opt-v4-types-grouping;
    }
    leaf data-checking {
      description
        "Perform data consistency check";
      type empty;
    }
    leaf error-message {
      description
        "Generate error message on inconsistency detection";
      type empty;
    }
  }

  grouping config-cef-tbl-cnst-chk-opt-v6-common-grouping {
    container auto-repair {
      description
        "Control auto-repair function";
      leaf delay {
        description
          "Delay in seconds";
        type uint16 {
          range "10..300";
        }
      }
      leaf holddown {
        description
          "Delay in seconds";
        type uint16 {
          range "300..3000";
        }
      }
    }
    container type {
      description
        "Type of consistency check to configure";
      uses config-cef-tbl-cnst-chk-opt-v6-types-grouping;
    }
    leaf data-checking {
      description
        "Perform data consistency check";
      type empty;
    }
    leaf error-message {
      description
        "Generate error message on inconsistency detection";
      type empty;
    }
  }

  grouping config-cef-tbl-dl-rt-type-pri-grouping {
    container priority {
      leaf priority1 {
        description
          "1st priority";
        type empty;
      }
      leaf priority2 {
        description
          "2nd priority";
        type empty;
      }
      leaf priority3 {
        description
          "3rd priority";
        type empty;
      }
      leaf priority4 {
        description
          "4th priority";
        type empty;
      }
    }
  }

  grouping config-cef-tbl-dl-rt-type-grouping {
    container catch-all {
      description
        "Any other route not matched (default P4)";
      uses config-cef-tbl-dl-rt-type-pri-grouping;
    }
    container connected-route {
      description
        "Directly connected route (default P2)";
      uses config-cef-tbl-dl-rt-type-pri-grouping;
    }
    container default-route {
      description
        "Default route, 0.0.0.0/0 or ::/0 (default P1)";
      uses config-cef-tbl-dl-rt-type-pri-grouping;
    }
    container receive-route {
      description
        "Receive route, local address on router (default P2)";
      uses config-cef-tbl-dl-rt-type-pri-grouping;
    }
    container recursive-dependents {
      description
        "Route with recursive dependents, matches next-hop
              of other recursive routes (default P1)";
      uses config-cef-tbl-dl-rt-type-pri-grouping;
    }
    container route-in-vrf {
      description
        "Route is in a VRF (default P3)";
      uses config-cef-tbl-dl-rt-type-pri-grouping;
    }
  }

  grouping config-cef-grouping {
    container cef {
      description
        "Cisco Express Forwarding";
      container table {
        description
          "Set CEF forwarding table characteristics";
        container output-chain {
          description
            "Set table output chain characteristics";
          container build {
            description
              "Set table output chain building characteristics";
            container favor {
              choice favor-choice {
                status deprecated;
                description
                  "Set which table output chain building characteristics to favor";
                leaf convergence-speed {
                  description
                    "Favor faster convergence";
                  type empty;
                }
                leaf memory-utilization {
                  description
                    "Favor smaller memory utilization";
                  type empty;
                }
              }
            }
            container indirection {
              description
                "Customize table output chain building indirection characteristics";
              leaf ipv4-to-mpls {
                description
                  "shared indirection object for IPv4 labeled prefixes";
                type empty;
              }
              leaf ipv6-to-mpls {
                description
                  "shared indirection object for IPv6 labeled prefixes";
                type empty;
              }
              leaf mpls-end-of-stack {
                description
                  "shared indirection object for MPLS disposition";
                type empty;
              }
              leaf mpls-non-end-of-stack {
                description
                  "shared indirection object for MPLS label switch";
                type empty;
              }
              leaf non-recursive-prefix {
                description
                  "non-recursive-prefix";
                type empty;
              }
              leaf recursive-prefix {
                description
                  "recursive-prefix";
                type empty;
              }
            }
            container inplace-modify {
              description
                "Customize table output chain building inplace modification characteristics";
              leaf load-sharing {
                description
                  "load sharing structures";
                type empty;
              }
              leaf push-counter {
                description
                  "push counter structures";
                type empty;
              }
            }
          }
        }
        container consistency-check {
          container ipv4 {
            description
              "IPv4 address family";
            uses config-cef-tbl-cnst-chk-opt-v4-common-grouping;
          }
          container ipv6 {
            description
              "IPv6 address family";
            uses config-cef-tbl-cnst-chk-opt-v6-common-grouping;
          }
        }
        container download {
          uses config-cef-tbl-dl-rt-type-grouping;
        }
        leaf rate-monitor-period {
          description
            "Period in minutes";
          type uint8 {
            range "1..60";
          }
        }
      }
    }
  }

  augment "/ios:native" {
    uses config-cef-grouping;
  }

  augment "/ios:native/ios:ip/ios:cef" {
    uses config-ip-cef-grouping;
  }

  augment "/ios:native/ios:ipv6/ios:cef" {
    uses config-ipv6-cef-grouping;
  }
}
