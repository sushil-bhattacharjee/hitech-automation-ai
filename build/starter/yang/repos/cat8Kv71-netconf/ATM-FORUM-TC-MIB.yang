/*
 * Generated by confdc --mib2yang-std
 * Source: mgmt/dmi/model/mib/src/ATM-FORUM-TC-MIB.mib
 */
/*
 * This YANG module has been generated by smidump 0.5.0:
 *
 *      smidump -f yang ATM-FORUM-TC-MIB
 *
 * Do not edit. Edit the source file instead!
 */

module ATM-FORUM-TC-MIB {

  namespace "urn:ietf:params:xml:ns:yang:smiv2:ATM-FORUM-TC-MIB";
  prefix ATM-FORUM-TC-MIB;

  import ietf-yang-smiv2 {
    prefix "smiv2";
  }

  typedef TruthValue {
    type enumeration {
      enum "true" {
        value "1";
      }
      enum "false" {
        value "2";
      }
    }
    description
     "Boolean values use this data type from RFC-1903";
  }

  typedef ClnpAddress {
    type binary {
      length "1..21";
    }
    description
     "CLNP address values use this data type from RFC-1238";
  }

  typedef AtmServiceCategory {
    type enumeration {
      enum "other" {
        value "1";
      }
      enum "cbr" {
        value "2";
      }
      enum "rtVbr" {
        value "3";
      }
      enum "nrtVbr" {
        value "4";
      }
      enum "abr" {
        value "5";
      }
      enum "ubr" {
        value "6";
      }
    }
    description
     "ATM Service Categories use this data type";
  }

  typedef AtmAddress {
    type binary {
      length "8|20";
    }
    description
     "ATM End-System Addresses";
  }

  typedef NetPrefix {
    type binary {
      length "8|13";
    }
    description
     "ATM End-System Addresses";
  }

  smiv2:alias "atmForum" {
    smiv2:oid "1.3.6.1.4.1.353";
  }

  smiv2:alias "atmForumAdmin" {
    smiv2:oid "1.3.6.1.4.1.353.1";
  }

  smiv2:alias "atmfTransmissionTypes" {
    smiv2:oid "1.3.6.1.4.1.353.1.2";
  }

  smiv2:alias "atmfUnknownType" {
    smiv2:oid "1.3.6.1.4.1.353.1.2.1";
  }

  smiv2:alias "atmfSonetSTS3c" {
    smiv2:oid "1.3.6.1.4.1.353.1.2.2";
  }

  smiv2:alias "atmfDs3" {
    smiv2:oid "1.3.6.1.4.1.353.1.2.3";
  }

  smiv2:alias "atmf4B5B" {
    smiv2:oid "1.3.6.1.4.1.353.1.2.4";
  }

  smiv2:alias "atmf8B10B" {
    smiv2:oid "1.3.6.1.4.1.353.1.2.5";
  }

  smiv2:alias "atmfSonetSTS12c" {
    smiv2:oid "1.3.6.1.4.1.353.1.2.6";
  }

  smiv2:alias "atmfE3" {
    smiv2:oid "1.3.6.1.4.1.353.1.2.7";
  }

  smiv2:alias "atmfT1" {
    smiv2:oid "1.3.6.1.4.1.353.1.2.8";
  }

  smiv2:alias "atmfE1" {
    smiv2:oid "1.3.6.1.4.1.353.1.2.9";
  }

  smiv2:alias "atmfMediaTypes" {
    smiv2:oid "1.3.6.1.4.1.353.1.3";
  }

  smiv2:alias "atmfMediaUnknownType" {
    smiv2:oid "1.3.6.1.4.1.353.1.3.1";
  }

  smiv2:alias "atmfMediaCoaxCable" {
    smiv2:oid "1.3.6.1.4.1.353.1.3.2";
  }

  smiv2:alias "atmfMediaSingleMode" {
    smiv2:oid "1.3.6.1.4.1.353.1.3.3";
  }

  smiv2:alias "atmfMediaMultiMode" {
    smiv2:oid "1.3.6.1.4.1.353.1.3.4";
  }

  smiv2:alias "atmfMediaStp" {
    smiv2:oid "1.3.6.1.4.1.353.1.3.5";
  }

  smiv2:alias "atmfMediaUtp" {
    smiv2:oid "1.3.6.1.4.1.353.1.3.6";
  }

  smiv2:alias "atmfTrafficDescrTypes" {
    smiv2:oid "1.3.6.1.4.1.353.1.4";
  }

  smiv2:alias "atmfNoDescriptor" {
    smiv2:oid "1.3.6.1.4.1.353.1.4.1";
  }

  smiv2:alias "atmfPeakRate" {
    smiv2:oid "1.3.6.1.4.1.353.1.4.2";
  }

  smiv2:alias "atmfNoClpNoScr" {
    smiv2:oid "1.3.6.1.4.1.353.1.4.3";
  }

  smiv2:alias "atmfClpNoTaggingNoScr" {
    smiv2:oid "1.3.6.1.4.1.353.1.4.4";
  }

  smiv2:alias "atmfClpTaggingNoScr" {
    smiv2:oid "1.3.6.1.4.1.353.1.4.5";
  }

  smiv2:alias "atmfNoClpScr" {
    smiv2:oid "1.3.6.1.4.1.353.1.4.6";
  }

  smiv2:alias "atmfClpNoTaggingScr" {
    smiv2:oid "1.3.6.1.4.1.353.1.4.7";
  }

  smiv2:alias "atmfClpTaggingScr" {
    smiv2:oid "1.3.6.1.4.1.353.1.4.8";
  }

  smiv2:alias "atmfClpNoTaggingMcr" {
    smiv2:oid "1.3.6.1.4.1.353.1.4.9";
  }

  smiv2:alias "atmfSrvcRegTypes" {
    smiv2:oid "1.3.6.1.4.1.353.1.5";
  }

  smiv2:alias "atmForumUni" {
    smiv2:oid "1.3.6.1.4.1.353.2";
  }

  smiv2:alias "atmfPhysicalGroup" {
    smiv2:oid "1.3.6.1.4.1.353.2.1";
  }

  smiv2:alias "atmfAtmLayerGroup" {
    smiv2:oid "1.3.6.1.4.1.353.2.2";
  }

  smiv2:alias "atmfAtmStatsGroup" {
    smiv2:oid "1.3.6.1.4.1.353.2.3";
  }

  smiv2:alias "atmfVpcGroup" {
    smiv2:oid "1.3.6.1.4.1.353.2.4";
  }

  smiv2:alias "atmfVccGroup" {
    smiv2:oid "1.3.6.1.4.1.353.2.5";
  }

  smiv2:alias "atmfAddressGroup" {
    smiv2:oid "1.3.6.1.4.1.353.2.6";
  }

  smiv2:alias "atmfNetPrefixGroup" {
    smiv2:oid "1.3.6.1.4.1.353.2.7";
  }

  smiv2:alias "atmfSrvcRegistryGroup" {
    smiv2:oid "1.3.6.1.4.1.353.2.8";
  }

  smiv2:alias "atmfVpcAbrGroup" {
    smiv2:oid "1.3.6.1.4.1.353.2.9";
  }

  smiv2:alias "atmfVccAbrGroup" {
    smiv2:oid "1.3.6.1.4.1.353.2.10";
  }

  smiv2:alias "atmfAddressRegistrationAdminGroup" {
    smiv2:oid "1.3.6.1.4.1.353.2.11";
  }

}
