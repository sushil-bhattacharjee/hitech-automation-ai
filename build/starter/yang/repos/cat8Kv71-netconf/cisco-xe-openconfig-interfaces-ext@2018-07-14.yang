module cisco-xe-openconfig-interfaces-ext{

  yang-version "1";

  // namespace
  namespace "http://cisco.com/ns/yang/cisco-xe-openconfig-interfaces-ext";

  prefix "oc-if-cisco";
  import openconfig-interfaces { prefix oc-if; }


  // import some basic types
  import openconfig-extensions { prefix oc-ext; }


  // meta
  organization 
    "Cisco Systems, Inc.";

  contact
    "Cisco Systems, Inc.
    Customer Service
    
    Postal: 170 W Tasman Drive
    San Jose, CA 95134

    Tel: +1 1800 553-NETS
    
    E-mail: cs-yang@cisco.com";

  description
    "Module to enable mapping for oc-interfaces.";

  revision "2018-07-14" {
    description
      "Removed hold-time augmentations as L2 hold-tome is not supported on IOS XE.";
    reference "1.0.2";
  }

  revision "2017-03-05" {
    description
      "Augment oc-interfaces to add hold-time leafs to oc state";
    reference "1.0.2";
  }

  revision "2017-02-25" {
    description
      "Augment oc-interfaces to add required hold-time leafs for Cisco platforms";
    reference "1.0.2";
  }


  augment "/oc-if:interfaces/oc-if:interface" +
            "/oc-if:config" {
              container bandwidth {
                leaf kilobits {
                  type uint32;
                  description
                    "Add bandwidth configuration for XE routers.";
               }
             }
          }

}
