/*
 * Generated by confdc --mib2yang-std
 * Source: mgmt/dmi/model/mib/src/NOTIFICATION-LOG-MIB.mib
 */
/*
 * This YANG module has been generated by smidump 0.5.0:
 *
 *      smidump -f yang NOTIFICATION-LOG-MIB
 *
 * Do not edit. Edit the source file instead!
 */

module NOTIFICATION-LOG-MIB {

  namespace "urn:ietf:params:xml:ns:yang:smiv2:NOTIFICATION-LOG-MIB";
  prefix NOTIFICATION-LOG-MIB;

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "IETF Distributed Management Working Group";

  contact
   "Ramanathan Kavasseri
    Cisco Systems, Inc.
    170 West Tasman Drive,
    San Jose CA 95134-1706.
    Phone: +1 408 527 2446
    Email: ramk@cisco.com";

  description
   "The MIB module for logging SNMP Notifications, that is, Traps
    and Informs.";

  revision 2000-11-27 {
    description
     "This is the initial version of this MIB.
      Published as RFC 3014";
  }


  container NOTIFICATION-LOG-MIB {
    config false;

    container nlmConfig {
      smiv2:oid "1.3.6.1.2.1.92.1.1";

      leaf nlmConfigGlobalEntryLimit {
        type uint32;
        description
         "The maximum number of notification entries that may be held
          in nlmLogTable for all nlmLogNames added together.  A particular
          setting does not guarantee that much data can be held.
          
          If an application changes the limit while there are
          Notifications in the log, the oldest Notifications MUST be
          discarded to bring the log down to the new limit - thus the
          value of nlmConfigGlobalEntryLimit MUST take precedence over
          the values of nlmConfigGlobalAgeOut and nlmConfigLogEntryLimit,
          even if the Notification being discarded has been present for
          fewer minutes than the value of nlmConfigGlobalAgeOut, or if
          the named log has fewer entries than that specified in
          nlmConfigLogEntryLimit.
          
          A value of 0 means no limit.
          
          Please be aware that contention between multiple managers
          trying to set this object to different values MAY affect the
          reliability and completeness of data seen by each manager.";
        smiv2:defval "0";
        smiv2:max-access "read-write";
        smiv2:oid "1.3.6.1.2.1.92.1.1.1";
      }

      leaf nlmConfigGlobalAgeOut {
        type uint32;
        units "minutes";
        description
         "The number of minutes a Notification SHOULD be kept in a log
          before it is automatically removed.
          
          If an application changes the value of nlmConfigGlobalAgeOut,
          Notifications older than the new time MAY be discarded to meet the
          new time.
          
          A value of 0 means no age out.
          
          Please be aware that contention between multiple managers
          trying to set this object to different values MAY affect the
          reliability and completeness of data seen by each manager.";
        smiv2:defval "1440";
        smiv2:max-access "read-write";
        smiv2:oid "1.3.6.1.2.1.92.1.1.2";
      }
    }

    container nlmStats {
      smiv2:oid "1.3.6.1.2.1.92.1.2";

      leaf nlmStatsGlobalNotificationsLogged {
        type yang:counter32;
        units "notifications";
        description
         "The number of Notifications put into the nlmLogTable.  This
          counts a Notification once for each log entry, so a Notification
           put into multiple logs is counted multiple times.";
        smiv2:max-access "read-only";
        smiv2:oid "1.3.6.1.2.1.92.1.2.1";
      }

      leaf nlmStatsGlobalNotificationsBumped {
        type yang:counter32;
        units "notifications";
        description
         "The number of log entries discarded to make room for a new entry
          due to lack of resources or the value of nlmConfigGlobalEntryLimit
          or nlmConfigLogEntryLimit.  This does not include entries discarded
          due to the value of nlmConfigGlobalAgeOut.";
        smiv2:max-access "read-only";
        smiv2:oid "1.3.6.1.2.1.92.1.2.2";
      }
    }

    container nlmConfigLogTable {
      description
       "A table of logging control entries.";
      smiv2:oid "1.3.6.1.2.1.92.1.1.3";

      list nlmConfigLogEntry {
        key "nlmLogName";
        description
         "A logging control entry.  Depending on the entry's storage type
          entries may be supplied by the system or created and deleted by
          applications using nlmConfigLogEntryStatus.";
        smiv2:oid "1.3.6.1.2.1.92.1.1.3.1";

        leaf nlmLogName {
          type snmp-framework:SnmpAdminString {
            length "0..32";
          }
          description
           "The name of the log.
            
            An implementation may allow multiple named logs, up to some
            implementation-specific limit (which may be none).  A
            zero-length log name is reserved for creation and deletion by
            the managed system, and MUST be used as the default log name by
            systems that do not support named logs.";
          smiv2:max-access "not-accessible";
          smiv2:oid "1.3.6.1.2.1.92.1.1.3.1.1";
        }

        leaf nlmConfigLogFilterName {
          type snmp-framework:SnmpAdminString {
            length "0..32";
          }
          description
           "A value of snmpNotifyFilterProfileName as used as an index
            into the snmpNotifyFilterTable in the SNMP Notification MIB,
            specifying the locally or remotely originated Notifications
            to be filtered out and not logged in this log.
            
            A zero-length value or a name that does not identify an
            existing entry in snmpNotifyFilterTable indicate no
            Notifications are to be logged in this log.";
          smiv2:defval "";
          smiv2:max-access "read-write";
          smiv2:oid "1.3.6.1.2.1.92.1.1.3.1.2";
        }

        leaf nlmConfigLogEntryLimit {
          type uint32;
          description
           "The maximum number of notification entries that can be held in
            nlmLogTable for this named log.  A particular setting does not
            guarantee that that much data can be held.
            
            If an application changes the limit while there are
            Notifications in the log, the oldest Notifications are discarded
            to bring the log down to the new limit.
            
            A value of 0 indicates no limit.
            
            Please be aware that contention between multiple managers
            trying to set this object to different values MAY affect the
            reliability and completeness of data seen by each manager.";
          smiv2:defval "0";
          smiv2:max-access "read-write";
          smiv2:oid "1.3.6.1.2.1.92.1.1.3.1.3";
        }

        leaf nlmConfigLogAdminStatus {
          type enumeration {
            enum "enabled" {
              value "1";
            }
            enum "disabled" {
              value "2";
            }
          }
          description
           "Control to enable or disable the log without otherwise
            disturbing the log's entry.
            
            Please be aware that contention between multiple managers
            trying to set this object to different values MAY affect the
            reliability and completeness of data seen by each manager.";
          smiv2:defval "enabled";
          smiv2:max-access "read-write";
          smiv2:oid "1.3.6.1.2.1.92.1.1.3.1.4";
        }

        leaf nlmConfigLogOperStatus {
          type enumeration {
            enum "disabled" {
              value "1";
            }
            enum "operational" {
              value "2";
            }
            enum "noFilter" {
              value "3";
            }
          }
          description
           "The operational status of this log:
            
            disabled  administratively disabled
            
            operational    administratively enabled and working
            
            noFilter  administratively enabled but either
                      nlmConfigLogFilterName is zero length
                      or does not name an existing entry in
                      snmpNotifyFilterTable";
          smiv2:max-access "read-only";
          smiv2:oid "1.3.6.1.2.1.92.1.1.3.1.5";
        }

        leaf nlmConfigLogStorageType {
          type snmpv2-tc:StorageType;
          description
           "The storage type of this conceptual row.";
          smiv2:max-access "read-write";
          smiv2:oid "1.3.6.1.2.1.92.1.1.3.1.6";
        }

        leaf nlmConfigLogEntryStatus {
          type snmpv2-tc:RowStatus;
          description
           "Control for creating and deleting entries.  Entries may be
            modified while active.
            
            For non-null-named logs, the managed system records the security
            credentials from the request that sets nlmConfigLogStatus
            to 'active' and uses that identity to apply access control to
            the objects in the Notification to decide if that Notification
            may be logged.";
          smiv2:max-access "read-write";
          smiv2:oid "1.3.6.1.2.1.92.1.1.3.1.7";
        }
      }
    }

    container nlmLogTable {
      description
       "A table of Notification log entries.
        
        It is an implementation-specific matter whether entries in this
        table are preserved across initializations of the management
        system.  In general one would expect that they are not.
        
        Note that keeping entries across initializations of the
        management system leads to some confusion with counters and
        TimeStamps, since both of those are based on sysUpTime, which
        resets on management initialization.  In this situation,
        counters apply only after the reset and nlmLogTime for entries
        made before the reset MUST be set to 0.";
      smiv2:oid "1.3.6.1.2.1.92.1.3.1";

      list nlmLogEntry {
        key "nlmLogName nlmLogIndex";
        description
         "A Notification log entry.
          
          Entries appear in this table when Notifications occur and pass
          filtering by nlmConfigLogFilterName and access control.  They are
          removed to make way for new entries due to lack of resources or
          the values of nlmConfigGlobalEntryLimit, nlmConfigGlobalAgeOut, or
          nlmConfigLogEntryLimit.
          
          If adding an entry would exceed nlmConfigGlobalEntryLimit or system
          resources in general, the oldest entry in any log SHOULD be removed
          to make room for the new one.
          
          If adding an entry would exceed nlmConfigLogEntryLimit the oldest
          entry in that log SHOULD be removed to make room for the new one.
          
          Before the managed system puts a locally-generated Notification
          into a non-null-named log it assures that the creator of the log
          has access to the information in the Notification.  If not it
          does not log that Notification in that log.";
        smiv2:oid "1.3.6.1.2.1.92.1.3.1.1";

        leaf nlmLogName {
          type leafref {
            path "/NOTIFICATION-LOG-MIB:NOTIFICATION-LOG-MIB/NOTIFICATION-LOG-MIB:nlmConfigLogTable/NOTIFICATION-LOG-MIB:nlmConfigLogEntry/NOTIFICATION-LOG-MIB:nlmLogName";
          }
        }

        leaf nlmLogIndex {
          type uint32 {
            range "1..4294967295";
          }
          description
           "A monotonically increasing integer for the sole purpose of
            indexing entries within the named log.  When it reaches the
            maximum value, an extremely unlikely event, the agent wraps the
            value back to 1.";
          smiv2:max-access "not-accessible";
          smiv2:oid "1.3.6.1.2.1.92.1.3.1.1.1";
        }

        leaf nlmLogTime {
          type yang:timestamp;
          description
           "The value of sysUpTime when the entry was placed in the log. If
            the entry occurred before the most recent management system
            initialization this object value MUST be set to zero.";
          smiv2:max-access "read-only";
          smiv2:oid "1.3.6.1.2.1.92.1.3.1.1.2";
        }

        leaf nlmLogDateAndTime {
          type snmpv2-tc:DateAndTime;
          description
           "The local date and time when the entry was logged, instantiated
            only by systems that have date and time capability.";
          smiv2:max-access "read-only";
          smiv2:oid "1.3.6.1.2.1.92.1.3.1.1.3";
        }

        leaf nlmLogEngineID {
          type snmp-framework:SnmpEngineID;
          description
           "The identification of the SNMP engine at which the Notification
            originated.
            
            If the log can contain Notifications from only one engine
            or the Trap is in SNMPv1 format, this object is a zero-length
            string.";
          smiv2:max-access "read-only";
          smiv2:oid "1.3.6.1.2.1.92.1.3.1.1.4";
        }

        leaf nlmLogEngineTAddress {
          type snmpv2-tc:TAddress;
          description
           "The transport service address of the SNMP engine from which the
            Notification was received, formatted according to the corresponding
            value of nlmLogEngineTDomain. This is used to identify the source
            of an SNMPv1 trap, since an nlmLogEngineId cannot be extracted
            from the SNMPv1 trap pdu.
            
            This object MUST always be instantiated, even if the log
            can contain Notifications from only one engine.
            
            Please be aware that the nlmLogEngineTAddress may not uniquely
            identify the SNMP engine from which the Notification was received.
            For example, if an SNMP engine uses DHCP or NAT to obtain
            ip addresses, the address it uses may be shared with other
            network devices, and hence will not uniquely identify the
            SNMP engine.";
          smiv2:max-access "read-only";
          smiv2:oid "1.3.6.1.2.1.92.1.3.1.1.5";
        }

        leaf nlmLogEngineTDomain {
          type snmpv2-tc:TDomain;
          description
           "Indicates the kind of transport service by which a Notification
            was received from an SNMP engine. nlmLogEngineTAddress contains
            the transport service address of the SNMP engine from which
            this Notification was received.
            
            Possible values for this object are presently found in the
            Transport Mappings for SNMPv2 document (RFC 1906 [8]).";
          smiv2:max-access "read-only";
          smiv2:oid "1.3.6.1.2.1.92.1.3.1.1.6";
        }

        leaf nlmLogContextEngineID {
          type snmp-framework:SnmpEngineID;
          description
           "If the Notification was received in a protocol which has a
            contextEngineID element like SNMPv3, this object has that value.
            Otherwise its value is a zero-length string.";
          smiv2:max-access "read-only";
          smiv2:oid "1.3.6.1.2.1.92.1.3.1.1.7";
        }

        leaf nlmLogContextName {
          type snmp-framework:SnmpAdminString;
          description
           "The name of the SNMP MIB context from which the Notification came.
            For SNMPv1 Traps this is the community string from the Trap.";
          smiv2:max-access "read-only";
          smiv2:oid "1.3.6.1.2.1.92.1.3.1.1.8";
        }

        leaf nlmLogNotificationID {
          type yang:object-identifier-128;
          description
           "The NOTIFICATION-TYPE object identifier of the Notification that
            occurred.";
          smiv2:max-access "read-only";
          smiv2:oid "1.3.6.1.2.1.92.1.3.1.1.9";
        }
      }
    }

    container nlmLogVariableTable {
      description
       "A table of variables to go with Notification log entries.";
      smiv2:oid "1.3.6.1.2.1.92.1.3.2";

      list nlmLogVariableEntry {
        key "nlmLogName nlmLogIndex nlmLogVariableIndex";
        description
         "A Notification log entry variable.
          
          Entries appear in this table when there are variables in
          the varbind list of a Notification in nlmLogTable.";
        smiv2:oid "1.3.6.1.2.1.92.1.3.2.1";

        leaf nlmLogName {
          type leafref {
            path "/NOTIFICATION-LOG-MIB:NOTIFICATION-LOG-MIB/NOTIFICATION-LOG-MIB:nlmConfigLogTable/NOTIFICATION-LOG-MIB:nlmConfigLogEntry/NOTIFICATION-LOG-MIB:nlmLogName";
          }
        }

        leaf nlmLogIndex {
          type leafref {
            path "/NOTIFICATION-LOG-MIB:NOTIFICATION-LOG-MIB/NOTIFICATION-LOG-MIB:nlmLogTable/NOTIFICATION-LOG-MIB:nlmLogEntry/NOTIFICATION-LOG-MIB:nlmLogIndex";
          }
        }

        leaf nlmLogVariableIndex {
          type uint32 {
            range "1..4294967295";
          }
          description
           "A monotonically increasing integer, starting at 1 for a given
            nlmLogIndex, for indexing variables within the logged
            Notification.";
          smiv2:max-access "not-accessible";
          smiv2:oid "1.3.6.1.2.1.92.1.3.2.1.1";
        }

        leaf nlmLogVariableID {
          type yang:object-identifier-128;
          description
           "The variable's object identifier.";
          smiv2:max-access "read-only";
          smiv2:oid "1.3.6.1.2.1.92.1.3.2.1.2";
        }

        leaf nlmLogVariableValueType {
          type enumeration {
            enum "counter32" {
              value "1";
            }
            enum "unsigned32" {
              value "2";
            }
            enum "timeTicks" {
              value "3";
            }
            enum "integer32" {
              value "4";
            }
            enum "ipAddress" {
              value "5";
            }
            enum "octetString" {
              value "6";
            }
            enum "objectId" {
              value "7";
            }
            enum "counter64" {
              value "8";
            }
            enum "opaque" {
              value "9";
            }
          }
          description
           "The type of the value.  One and only one of the value
            objects that follow must be instantiated, based on this type.";
          smiv2:max-access "read-only";
          smiv2:oid "1.3.6.1.2.1.92.1.3.2.1.3";
        }

        leaf nlmLogVariableCounter32Val {
          type yang:counter32;
          description
           "The value when nlmLogVariableType is 'counter32'.";
          smiv2:max-access "read-only";
          smiv2:oid "1.3.6.1.2.1.92.1.3.2.1.4";
        }

        leaf nlmLogVariableUnsigned32Val {
          type uint32;
          description
           "The value when nlmLogVariableType is 'unsigned32'.";
          smiv2:max-access "read-only";
          smiv2:oid "1.3.6.1.2.1.92.1.3.2.1.5";
        }

        leaf nlmLogVariableTimeTicksVal {
          type yang:timeticks;
          description
           "The value when nlmLogVariableType is 'timeTicks'.";
          smiv2:max-access "read-only";
          smiv2:oid "1.3.6.1.2.1.92.1.3.2.1.6";
        }

        leaf nlmLogVariableInteger32Val {
          type int32;
          description
           "The value when nlmLogVariableType is 'integer32'.";
          smiv2:max-access "read-only";
          smiv2:oid "1.3.6.1.2.1.92.1.3.2.1.7";
        }

        leaf nlmLogVariableOctetStringVal {
          type binary;
          description
           "The value when nlmLogVariableType is 'octetString'.";
          smiv2:max-access "read-only";
          smiv2:oid "1.3.6.1.2.1.92.1.3.2.1.8";
        }

        leaf nlmLogVariableIpAddressVal {
          type inet:ipv4-address;
          description
           "The value when nlmLogVariableType is 'ipAddress'.
            Although this seems to be unfriendly for IPv6, we
            have to recognize that there are a number of older
            MIBs that do contain an IPv4 format address, known
            as IpAddress.
            
            IPv6 addresses are represented using TAddress or
            InetAddress, and so the underlying datatype is
            OCTET STRING, and their value would be stored in
            the nlmLogVariableOctetStringVal column.";
          smiv2:max-access "read-only";
          smiv2:oid "1.3.6.1.2.1.92.1.3.2.1.9";
        }

        leaf nlmLogVariableOidVal {
          type yang:object-identifier-128;
          description
           "The value when nlmLogVariableType is 'objectId'.";
          smiv2:max-access "read-only";
          smiv2:oid "1.3.6.1.2.1.92.1.3.2.1.10";
        }

        leaf nlmLogVariableCounter64Val {
          type yang:counter64;
          description
           "The value when nlmLogVariableType is 'counter64'.";
          smiv2:max-access "read-only";
          smiv2:oid "1.3.6.1.2.1.92.1.3.2.1.11";
        }

        leaf nlmLogVariableOpaqueVal {
          type binary;
          description
           "The value when nlmLogVariableType is 'opaque'.";
          smiv2:max-access "read-only";
          smiv2:oid "1.3.6.1.2.1.92.1.3.2.1.12";
        }
      }
    }
  }

  smiv2:alias "nlmStatsLogTable" {
    description
     "A table of Notification log statistics entries.";
    smiv2:oid "1.3.6.1.2.1.92.1.2.3";
  }

  smiv2:alias "nlmStatsLogEntry" {
    description
     "A Notification log statistics entry.";
    smiv2:oid "1.3.6.1.2.1.92.1.2.3.1";
  }

  augment "/NOTIFICATION-LOG-MIB:NOTIFICATION-LOG-MIB/NOTIFICATION-LOG-MIB:nlmConfigLogTable/NOTIFICATION-LOG-MIB:nlmConfigLogEntry" {
    description
     "A Notification log statistics entry.";
    smiv2:oid "1.3.6.1.2.1.92.1.2.3.1";

    leaf nlmStatsLogNotificationsLogged {
      type yang:counter32;
      units "notifications";
      description
       "The number of Notifications put in this named log.";
      smiv2:max-access "read-only";
      smiv2:oid "1.3.6.1.2.1.92.1.2.3.1.1";
    }

    leaf nlmStatsLogNotificationsBumped {
      type yang:counter32;
      units "notifications";
      description
       "The number of log entries discarded from this named log to make
        room for a new entry due to lack of resources or the value of
        nlmConfigGlobalEntryLimit or nlmConfigLogEntryLimit.  This does not
        include entries discarded due to the value of
        nlmConfigGlobalAgeOut.";
      smiv2:max-access "read-only";
      smiv2:oid "1.3.6.1.2.1.92.1.2.3.1.2";
    }
  }

  smiv2:alias "notificationLogMIB" {
    smiv2:oid "1.3.6.1.2.1.92";
  }

  smiv2:alias "notificationLogMIBObjects" {
    smiv2:oid "1.3.6.1.2.1.92.1";
  }

  smiv2:alias "nlmConfig" {
    smiv2:oid "1.3.6.1.2.1.92.1.1";
  }

  smiv2:alias "nlmStats" {
    smiv2:oid "1.3.6.1.2.1.92.1.2";
  }

  smiv2:alias "nlmLog" {
    smiv2:oid "1.3.6.1.2.1.92.1.3";
  }

  smiv2:alias "notificationLogMIBConformance" {
    smiv2:oid "1.3.6.1.2.1.92.3";
  }

  smiv2:alias "notificationLogMIBCompliances" {
    smiv2:oid "1.3.6.1.2.1.92.3.1";
  }

  smiv2:alias "notificationLogMIBGroups" {
    smiv2:oid "1.3.6.1.2.1.92.3.2";
  }

}
