module Cisco-IOS-XE-ip-sla-events {
  yang-version 1;
  namespace "http://cisco.com/ns/yang/Cisco-IOS-XE-ip-sla-events";
  prefix ip-sla-ios-xe-events;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IPSLA Reaction Notification.
     Copyright (c) 2019-2020 by Cisco Systems, Inc.
     All rights reserved.";

  revision 2020-11-01 {
    description
      "- Added new enum for IPSLA HTTPS operation type.
       - Extended the model to support IPSLA HTTPS reaction data.";
    reference
      "2.1.0";
    cisco-semver:module-version "2.1.0";
  }
  revision 2020-07-01 {
    description
      "- Remove unused empty container ip-sla-events";
    reference
      "2.0.0";
    cisco-semver:module-version "2.0.0";
  }
  revision 2020-03-01 {
    description
      "Initial revision";
    reference
      "1.0.0";
    cisco-semver:module-version "1.0.0";
  }

  typedef sla-notification-severity {
    type enumeration {
      enum critical {
        value 0;
        description
          "Notification severity - critical";
      }
      enum major {
        value 1;
        description
          "Notification severity - major";
      }
      enum minor {
        value 2;
        description
          "Notification severity - minor";
      }
    }
    description
      "Notification severity";
  }

  typedef ipsla-threshold-type {
    type enumeration {
      enum threshold-type-unknown {
        value 0;
        description
          "Unknown threshold type";
      }
      enum immediate {
        value 1;
        description
          "Immediate threshold type - React immediately when the threshold values are violated";
      }
      enum consecutive {
        value 2;
        description
          "Consecutive threshold type - React after N consecutive occurrences of threshold violations";
      }
      enum xofy {
        value 3;
        description
          "XofY threshold type - React X out of Y occurrences of threshold violations";
      }
      enum average {
        value 4;
        description
          "Average threshold type - React when average over N attempts are violating the threshold values";
      }
    }
    description
      "IPSLA Reaction Threshold Type";
  }

  typedef ipsla-operation-type {
    type enumeration {
      enum unknown {
        value 0;
        description
          "Unknown probe type";
      }
      enum udp-echo {
        value 1;
        description
          "UDP Echo operation";
      }
      enum udp-jitter {
        value 2;
        description
          "UDP Jitter operation";
      }
      enum icmp-jitter {
        value 3;
        description
          "ICMP Jitter operation";
      }
      enum y1731-delay {
        value 4;
        description
          "Y1731 Ethernet OAM Performance Delay Measurement
           operation";
      }
      enum y1731-loss {
        value 5;
        description
          "Y1731 Ethernet OAM Performance Loss Measurement
           operation";
      }
      enum path-jitter {
        value 6;
        description
          "Path Discovered ICMP Jitter operation";
      }
      enum icmp-echo {
        value 7;
        description
          "ICMP Echo operation";
      }
      enum path-echo {
        value 8;
        description
          "Path Discovered ICMP Echo operation";
      }
      enum tcp-connect {
        value 9;
        description
          "TCP Connect operation";
      }
      enum http {
        value 10;
        description
          "HTTP operation";
      }
      enum dns {
        value 11;
        description
          "DNS operation";
      }
      enum dhcp {
        value 12;
        description
          "DHCP operation";
      }
      enum ftp {
        value 13;
        description
          "FTP operation";
      }
      enum mpls-lsp-ping {
        value 14;
        description
          "MPLS lsp ping operation";
      }
      enum mpls-lsp-trace {
        value 15;
        description
          "MPLS lsp trace operation";
      }
      enum mpls-lsp-pseudowire-ping {
        value 16;
        description
          "MPLS lsp pseudowire ping operation";
      }
      enum https {
        value 17;
        description
          "HTTPS operation";
      }
    }
    description
      "IPSLA probe type";
  }

  typedef ipsla-react-type {
    type enumeration {
      enum react-unknown {
        value 0;
        description
          "Unknown reaction monitoring type";
      }
      enum rtt {
        value 1;
        description
          "Monitoring of Round Trip Time";
      }
      enum jitter-sd {
        value 2;
        description
          "Monitoring of Jitter average changes in the
           direction from source to destination";
      }
      enum jitter-ds {
        value 3;
        description
          "Monitoring of average jitter in the direction from
           destination to source";
      }
      enum packet-loss-sd {
        value 4;
        description
          "Monitoring of packet loss in the direction from
           source to destination";
      }
      enum packet-loss-ds {
        value 5;
        description
          "Monitoring of packet loss in the direction
           from destination to source";
      }
      enum mos {
        value 6;
        description
          "Monitoring of MOS score";
      }
      enum timeout {
        value 7;
        description
          "Monitoring of timeout occurrences";
      }
      enum connection-loss {
        value 8;
        description
          "Monitoring of connection loss occurrences";
      }
      enum verify-error {
        value 9;
        description
          "Monitoring of verify error occurrences";
      }
      enum jitter {
        value 10;
        description
          "Monitoring of average jitter in both the
           directions";
      }
      enum icpif {
        value 11;
        description
          "Monitoring of calculated planning impairment
           factor";
      }
      enum packet-mia {
        value 12;
        description
          "Monitoring of packets missing in action";
      }
      enum packet-late-arrival {
        value 13;
        description
          "Monitoring of packets arriving late";
      }
      enum packet-out-of-seq {
        value 14;
        description
          "Monitoring of packets arriving out of sequence";
      }
      enum max-of-positive-sd {
        value 15;
        description
          "Monitoring of maximum positive jitter in the
           direction from source to destination";
      }
      enum max-of-negative-sd {
        value 16;
        description
          "Monitoring of maximum negative jitter in the
           direction from source to destination";
      }
      enum max-of-positive-ds {
        value 17;
        description
          "Monitoring of maximum positive jitter in the
           direction from destination to source";
      }
      enum max-of-negative-ds {
        value 18;
        description
          "Monitoring of maximum negative jitter in the
           direction from destination to source";
      }
      enum inter-arrival-jitter-ds {
        value 19;
        description
          "Monitoring of inter-arrival jitter in the
           direction from source to destination";
      }
      enum frame-loss-ratio-percent-ds {
        value 20;
        description
          "Monitoring of frame loss ration percentage in the
           direction from destination to source";
      }
      enum frame-loss-ratio-percent-sd {
        value 21;
        description
          "Monitoring of frame loss ration percentage in the
           direction from source to destination";
      }
      enum successive-packet-loss {
        value 22;
        description
          "Monitoring of successive packet loss";
      }
      enum max-of-latency-ds {
        value 23;
        description
          "Monitoring of maximum latency in the direction
           from destination to source";
      }
      enum max-of-latency-sd {
        value 24;
        description
          "Monitoring of maximum latency in the direction
           from source to destination";
      }
      enum avg-latency-ds {
        value 25;
        description
          "Monitoring of average latency in the direction
           from destination to source";
      }
      enum avg-latency-sd {
        value 26;
        description
          "Monitoring of average latency in the direction
           from source to destination";
      }
      enum packet-loss {
        value 27;
        description
          "Monitoring of packet loss in both the directions";
      }
      enum inter-arrival-jitter-sd {
        value 28;
        description
          "Monitoring of inter-arrival jitter in the
           direction from source to destination";
      }
      enum unavailable-sd {
        value 29;
        description
          "Monitoring of unavailability percentage used for
           frame loss ratio in the direction from source to destination";
      }
      enum unavailable-ds {
        value 30;
        description
          "Monitoring of unavailability percentage used for
           frame loss ratio in the direction from destination to source";
      }
      enum percentile-rtt {
        value 31;
        description
          "Monitoring of percentile Round Trip Time";
      }
      enum percentile-max-of-latency-sd {
        value 32;
        description
          "Monitoring of percentile maximum latency in the
           direction from source to destination";
      }
      enum percentile-max-of-latency-ds {
        value 33;
        description
          "Monitoring of percentile maximum latency in the
           direction from destination to source";
      }
      enum percentile-avg-latency-sd {
        value 34;
        description
          "Monitoring of percentile latency average in the
           direction from source to destination";
      }
      enum percentile-avg-latency-ds {
        value 35;
        description
          "Monitoring of percentile latency average in the
           direction from destination to source";
      }
      enum percentile-jitter-sd {
        value 36;
        description
          "Monitoring of percentile jitter average in the
           direction from source to destination";
      }
      enum percentile-jitter-ds {
        value 37;
        description
          "Monitoring of percentile jitter average in the
           direction from destination to source";
      }
      enum percentile-jitter {
        value 38;
        description
          "Monitoring of percentile Jitter average in
           both the directions";
      }
      enum over-threshold {
        value 39;
        description
          "Monitoring of Round Trip Times over threshold";
      }
      enum protocol-specific-error {
        value 40;
        description
          "Monitoring of protocol specific error
           occurrences";
      }
      enum two-way-pos-jitter {
        value 41;
        description
          "Monitoring of two way positive jitter";
      }
      enum two-way-neg-jitter {
        value 42;
        description
          "Monitoring of two way negative jitter";
      }
    }
    description
      "IPSLA Reaction types";
  }

  typedef ipsla-y1731-sub-type {
    type enumeration {
      enum sla-y1731-unknown {
        value 0;
        description
          "Unknown Y1731 delay/loss type";
      }
      enum sla-y1731-delay-1dm {
        value 1;
        description
          "Y1731 Delay 1DM type";
      }
      enum sla-y1731-delay-dmm {
        value 2;
        description
          "Y1731 Delay DMM type";
      }
      enum sla-y1731-delay-dmmv1 {
        value 3;
        description
          "Y1731 Delay DMMv1 type";
      }
      enum sla-y1731-loss-lmm {
        value 4;
        description
          "Y1731 Loss LMM type";
      }
      enum sla-y1731-loss-slm {
        value 5;
        description
          "Y1731 Loss SLM type";
      }
    }
    description
      "IPSLA Y1731 Delay/Loss operation sub-types";
  }

  typedef ipsla-react-status {
    type enumeration {
      enum status-unknown {
        value 0;
        description
          "Unknown Y1731 delay/loss type";
      }
      enum occurred {
        value 1;
        description
          "Reaction occurred";
      }
      enum cleared {
        value 2;
        description
          "Reaction cleared";
      }
      enum exceeded-threshold {
        value 3;
        description
          "Reaction occurred as the monitored value exceeds the configured threshold value";
      }
      enum below-threshold {
        value 4;
        description
          "Reaction occurred as the monitored value falls below the configured threshold value";
      }
    }
    description
      "IPSLA Reaction Status";
  }

  typedef ipsla-probe-type {
    type enumeration {
      enum probe-type-unknown {
        value 0;
        description
          "Unknown probe type";
      }
      enum ipv6 {
        value 1;
        description
          "IPv6 probe type";
      }
      enum ipv4 {
        value 2;
        description
          "IPv4 probe type";
      }
    }
    description
      "IPSLA Probe type";
  }

  typedef ipsla-threshold-type-value {
    type enumeration {
      enum xofy-value {
        value 0;
        description
          "Xofy threshold type value";
      }
      enum consecutive-value {
        value 1;
        description
          "Consecutive threshold type value";
      }
      enum average-value {
        value 2;
        description
          "Average threshold type value";
      }
      enum immediate-value {
        value 3;
        description
          "Immediate threshold type value";
      }
    }
    description
      "Value of the IPSLA threshold type";
  }

  typedef ipsla-oper-data-type {
    type enumeration {
      enum dhcp-oper-data {
        value 0;
        description
          "IPSLA DHCP operation data";
      }
      enum dns-oper-data {
        value 1;
        description
          "IPSLA DNS operation data";
      }
      enum ftp-oper-data {
        value 2;
        description
          "IPSLA FTP operation data";
      }
      enum http-oper-data {
        value 3;
        description
          "IPSLA HTTP operation data";
      }
      enum icmp-echo-oper-data {
        value 4;
        description
          "IPSLA ICMP-echo operation data";
      }
      enum icmp-jitter-oper-data {
        value 5;
        description
          "IPSLA ICMP-jitter operation data";
      }
      enum lsp-ping-oper-data {
        value 6;
        description
          "IPSLA MPLS LSP ping operation data";
      }
      enum lsp-trace-oper-data {
        value 7;
        description
          "IPSLA MPLS LSP trace operation data";
      }
      enum lsp-ping-pseudowire-oper-data {
        value 8;
        description
          "IPSLA MPLS LSP pseudowire ping operation data";
      }
      enum path-echo-oper-data {
        value 9;
        description
          "IPSLA Path-echo operation data";
      }
      enum path-jitter-oper-data {
        value 10;
        description
          "IPSLA Path-jitter operation data";
      }
      enum tcp-connect-oper-data {
        value 11;
        description
          "IPSLA TCP-connect operation data";
      }
      enum udp-echo-oper-data {
        value 12;
        description
          "IPSLA UDP-echo operation data";
      }
      enum udp-jitter-oper-data {
        value 13;
        description
          "IPSLA UDP-jitter operation data";
      }
      enum y1731-delay-oper-data {
        value 14;
        description
          "IPSLA Y1731 Delay operation data";
      }
      enum y1731-loss-oper-data {
        value 15;
        description
          "IPSLA Y1731 Loss operation data";
      }
      enum https-oper-data {
        value 16;
        description
          "IPSLA HTTPS operation data";
      }
    }
    description
      "IPSLA operation data type";
  }

  typedef ipsla-ftp-mode-type {
    type enumeration {
      enum active {
        value 0;
        description
          "Active Mode";
      }
      enum passive {
        value 1;
        description
          "Passive Mode";
      }
    }
    description
      "IPSLA FTP operation mode";
  }

  typedef ipsla-precision-type {
    type enumeration {
      enum milliseconds {
        value 0;
        description
          "Milliseconds precision";
      }
      enum microseconds {
        value 1;
        description
          "Microseconds precision";
      }
    }
    description
      "Precision of the IPSLA operation";
  }

  grouping threshold-xofy-value {
    description
      "IPSLA Reaction threshold type - xofy type";
    leaf x-value {
      type uint32;
      description
        "Value of X when the threshold type is xofy";
    }
    leaf y-value {
      type uint32;
      description
        "Value of Y when the threshold type is xofy";
    }
  }

  grouping ipsla-react-data {
    description
      "IPSLA Reaction threshold value of the given threshold
       type";
    leaf threshold-type {
      type ip-sla-ios-xe-events:ipsla-threshold-type;
      description
        "IPSLA reaction threshold type";
    }
    leaf threshold-rising {
      type uint64;
      description
        "IPSLA Reaction threshold upper limit";
    }
    leaf threshold-falling {
      type uint64;
      description
        "IPSLA Reaction threshold falling limit";
    }
    choice threshold-value-choice {
      description
        "IPSLA Reaction threshold type's value based
         on the threshold type";
      case xofy-value {
        container xofy {
          description
            "Value of the xofy threshold type";
          uses ip-sla-ios-xe-events:threshold-xofy-value;
        }
      }
      case consecutive-value {
        leaf consecutive {
          type uint32;
          description
            "Value of the consecutive threshold type";
        }
      }
      case average-value {
        leaf average {
          type uint32;
          description
            "Value of the average threshold type";
        }
      }
      case immediate-value {
        leaf immediate {
          type boolean;
          description
            "Value of the immediate threshold type";
        }
      }
    }
  }

  grouping ipsla-udp-tcp-oper-type-data {
    description
      "IPSLA operation data of UDP and TCP based
       operations";
    leaf destination-address {
      type inet:ip-address;
      description
        "Destination address of the IPSLA operation";
    }
    leaf source-address {
      type inet:ip-address;
      description
        "Source address of the IPSLA operation";
    }
    leaf dest-port {
      type uint16;
      description
        "Destination port of the IPSLA operation";
    }
    leaf source-port {
      type uint16;
      description
        "Source port of the IPSLA operation";
    }
    leaf vrf-name {
      type string;
      description
        "VRF Name";
    }
  }

  grouping ipsla-icmp-oper-type-data {
    description
      "IPSLA operation data of ICMP based operations";
    leaf destination-address {
      type inet:ip-address;
      description
        "Destination address of the IPSLA operation";
    }
    leaf source-address {
      type inet:ip-address;
      description
        "Source address of the IPSLA operation";
    }
    leaf vrf-name {
      type string;
      description
        "VRF Name";
    }
  }

  grouping ipsla-dns-oper-type-data {
    description
      "IPSLA DNS operation data";
    leaf target-name {
      type string;
      description
        "Target Name of the operation";
    }
    leaf name-server {
      type inet:ip-address;
      description
        "Name server address";
    }
    leaf source-address {
      type inet:ip-address;
      description
        "Source address of the IPSLA operation";
    }
    leaf source-port {
      type uint16;
      description
        "Source port of the IPSLA operation";
    }
    leaf vrf-name {
      type string;
      description
        "VRF Name";
    }
  }

  grouping ipsla-dhcp-oper-type-data {
    description
      "IPSLA DHCP operation data";
    leaf destination-address {
      type inet:ip-address;
      description
        "Destination address of the IPSLA operation";
    }
    leaf source-address {
      type inet:ip-address;
      description
        "Source address of the IPSLA operation";
    }
  }

  grouping ipsla-ftp-oper-type-data {
    description
      "IPSLA FTP operation data";
    leaf url {
      type string;
      description
        "URL of the IPSLA operation";
    }
    leaf source-address {
      type inet:ip-address;
      description
        "Source address of the IPSLA operation";
    }
    leaf mode {
      type ip-sla-ios-xe-events:ipsla-ftp-mode-type;
      description
        "FTP mode of the IPSLA operation";
    }
    leaf vrf-name {
      type string;
      description
        "VRF Name";
    }
  }

  grouping ipsla-http-oper-type-data {
    description
      "IPSLA HTTP operation data";
    leaf destination-address {
      type inet:ip-address;
      description
        "Destination address of the IPSLA operation";
    }
    leaf url {
      type string;
      description
        "URL of the IPSLA operation";
    }
    leaf name-server {
      type inet:ip-address;
      description
        "Name server address";
    }
    leaf source-address {
      type inet:ip-address;
      description
        "Source address of the IPSLA operation";
    }
    leaf dest-port {
      type uint16;
      description
        "Destination port of the IPSLA operation";
    }
    leaf source-port {
      type uint16;
      description
        "Source port of the IPSLA operation";
    }
    leaf vrf-name {
      type string;
      description
        "VRF Name";
    }
  }

  grouping ipsla-lsp-ping-trace-oper-type-data {
    description
      "IPSLA operation data of the MPLS LSP ping and trace
       operation";
    leaf target-address {
      type inet:ip-address;
      description
        "Target address of the IPSLA operation";
    }
    leaf lsp-selector {
      type inet:ip-address;
      description
        "LSP selector which specifies a valid 127/8 address";
    }
    leaf source-address {
      type inet:ip-address;
      description
        "Source address of the IPSLA operation";
    }
  }

  grouping ipsla-lsp-pseudowire-oper-type-data {
    description
      "IPSLA MPLS LSP pseudowire operation data";
    leaf target-address {
      type inet:ip-address;
      description
        "Target address of the IPSLA operation";
    }
    leaf vccv-id {
      type uint32;
      description
        "MPLS LSP pseudowire VCCV ID";
    }
    leaf source-address {
      type inet:ip-address;
      description
        "Source address of the IPSLA operation";
    }
  }

  grouping ipsla-y1731-oper-type-data {
    description
      "IPSLA Y1731 delay and loss operation data";
    leaf y1731-sub-type {
      type ip-sla-ios-xe-events:ipsla-y1731-sub-type;
      description
        "Type of the Y1731 Delay/Loss operation";
    }
    leaf domain-name {
      type string;
      description
        "Name of the Ethernet Connectivity Fault Management (CFM)
         maintenance domain specified in the IPSLA operation";
    }
    leaf destination-mpid {
      type uint32;
      description
        "Destination maintenance endpoint identification
         number specified in the IPSLA operation";
    }
    leaf source-mpid {
      type uint32;
      description
        "Source maintenance endpoint identification
         number specified in the IPSLA operation";
    }
    leaf cos {
      type uint8;
      description
        "Class of Service specified in the IPSLA
         operation";
    }
  }

  grouping ipsla-https-oper-type-data {
    description
      "IPSLA HTTPS operation data";
    leaf dest-addr {
      type inet:ip-address;
      description
        "Destination address of the IPSLA HTTPS operation";
    }
    leaf url {
      type string;
      description
        "URL of the IPSLA HTTPS operation";
    }
    leaf name-server {
      type inet:ip-address;
      description
        "Name server address of the IPSLA HTTPS operation";
    }
    leaf dest-port {
      type uint16;
      description
        "Destination port of the IPSLA HTTPS operation";
    }
    leaf vrf-name {
      type string;
      description
        "VRF name of the IPSLA HTTPS operation";
    }
  }

  grouping ipsla-oper-data {
    description
      "IPSLA operation data";
    choice oper-data-type-choice {
      description
        "IPSLA operation type";
      case dhcp-oper-data {
        container dhcp-oper-data {
          description
            "DHCP operation data";
          uses ip-sla-ios-xe-events:ipsla-dhcp-oper-type-data;
        }
      }
      case dns-oper-data {
        container dns-oper-data {
          description
            "DNS operation data";
          uses ip-sla-ios-xe-events:ipsla-dns-oper-type-data;
        }
      }
      case ftp-oper-data {
        container ftp-oper-data {
          description
            "FTP operation data";
          uses ip-sla-ios-xe-events:ipsla-ftp-oper-type-data;
        }
      }
      case http-oper-data {
        container http-oper-data {
          description
            "HTTP operation data";
          uses ip-sla-ios-xe-events:ipsla-http-oper-type-data;
        }
      }
      case icmp-echo-oper-data {
        container icmp-echo-oper-data {
          description
            "ICMP echo operation data";
          uses ip-sla-ios-xe-events:ipsla-icmp-oper-type-data;
        }
      }
      case icmp-jitter-oper-data {
        container icmp-jitter-oper-data {
          description
            "ICMP jitter operation data";
          uses ip-sla-ios-xe-events:ipsla-icmp-oper-type-data;
        }
      }
      case lsp-ping-oper-data {
        container lsp-ping-oper-data {
          description
            "MPLS LSP ping operation data";
          uses ip-sla-ios-xe-events:ipsla-lsp-ping-trace-oper-type-data;
        }
      }
      case lsp-trace-oper-data {
        container lsp-trace-oper-data {
          description
            "MPLS LSP trace operation data";
          uses ip-sla-ios-xe-events:ipsla-lsp-ping-trace-oper-type-data;
        }
      }
      case lsp-ping-pseudowire-oper-data {
        container lsp-pseudowire-oper-data {
          description
            "MPLS LSP pseudowire operation data";
          uses ip-sla-ios-xe-events:ipsla-lsp-pseudowire-oper-type-data;
        }
      }
      case path-echo-oper-data {
        container path-echo-oper-data {
          description
            "Path echo operation data";
          uses ip-sla-ios-xe-events:ipsla-icmp-oper-type-data;
        }
      }
      case path-jitter-oper-data {
        container path-jitter-oper-data {
          description
            "Path jitter operation data";
          uses ip-sla-ios-xe-events:ipsla-icmp-oper-type-data;
        }
      }
      case tcp-connect-oper-data {
        container tcp-connect-oper-data {
          description
            "TCP connect operation data";
          uses ip-sla-ios-xe-events:ipsla-udp-tcp-oper-type-data;
        }
      }
      case udp-echo-oper-data {
        container udp-echo-oper-data {
          description
            "UDP echo operation data";
          uses ip-sla-ios-xe-events:ipsla-udp-tcp-oper-type-data;
        }
      }
      case udp-jitter-oper-data {
        container udp-jitter-oper-data {
          description
            "UDP Jitter operation data";
          uses ip-sla-ios-xe-events:ipsla-udp-tcp-oper-type-data;
        }
      }
      case y1731-delay-oper-data {
        container y1731-delay-oper-data {
          description
            "Y1731 Delay operation data";
          uses ip-sla-ios-xe-events:ipsla-y1731-oper-type-data;
        }
      }
      case y1731-loss-oper-data {
        container y1731-loss-oper-data {
          description
            "Y1731 Loss operation data";
          uses ip-sla-ios-xe-events:ipsla-y1731-oper-type-data;
        }
      }
      case https-oper-data {
        container https-oper-data {
          description
            "HTTPS operation data";
          uses ip-sla-ios-xe-events:ipsla-https-oper-type-data;
        }
      }
    }
  }

  grouping ipsla-react-update-data {
    description
      "IPSLA Reaction Update";
    leaf severity {
      type ip-sla-ios-xe-events:sla-notification-severity;
      description
        "Event severity";
    }
    leaf oper-id {
      type uint32;
      description
        "IPSLA operation Identifier";
    }
    leaf probe-type {
      type ip-sla-ios-xe-events:ipsla-probe-type;
      description
        "IPv6 Probe";
    }
    leaf oper-type {
      type ip-sla-ios-xe-events:ipsla-operation-type;
      description
        "IPSLA operation Type";
    }
    leaf react-type {
      type ip-sla-ios-xe-events:ipsla-react-type;
      description
        "IPSLA Reaction Type";
    }
    leaf react-status {
      type ip-sla-ios-xe-events:ipsla-react-status;
      description
        "IPSLA Reaction occurred status";
    }
    leaf react-value {
      type uint32;
      description
        "IPSLA Reaction value that violated the configured
         rising and falling threshold values";
    }
    leaf precision {
      type ip-sla-ios-xe-events:ipsla-precision-type;
      description
        "Precision of the IPSLA operation";
    }
    container react-data {
      description
        "IPSLA Reaction data";
      uses ip-sla-ios-xe-events:ipsla-react-data;
    }
    container oper-data {
      description
        "IPSLA operation data";
      uses ip-sla-ios-xe-events:ipsla-oper-data;
    }
  }

  notification ipsla-reaction-update {
    description
      "IPSLA Reaction Update Notification";
    uses ip-sla-ios-xe-events:ipsla-react-update-data;
  }
}
