module policy-types {
  yang-version 1;
  namespace "urn:ietf:params:xml:ns:yang:c3pl-types";
  prefix policy-types;

  import cisco-semver {
    prefix cisco-semver;
  }
  import ietf-diffserv-classifier {
    prefix classifier;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com

     Editor:   Nazanin Magharei
               <mailto:nmaghare@cisco.com>";
  description
    "This module contains a collection of YANG groupings
     in filter configurations for policy model.";

  revision 2019-07-01 {
    description
      "Establish semantic version baseline";
    cisco-semver:module-version "1.0.0";
  }
  revision 2013-10-07 {
    description
      "first revision";
    reference
      "TBD";
  }

  identity policy-type {
    description
      "
       This is identity of base policy-type";
  }

  identity qos {
    base policy-type;
    description
      "
       Policy-type QOS (quality of service)";
  }

  identity pbr {
    base policy-type;
    description
      "
       Policy-type PBR (policy based routing)";
  }

  identity perf-mon {
    base policy-type;
    description
      "
       Policy-type PERF-MON (performance monitoring)";
  }

  identity access-control {
    base policy-type;
    description
      "
       Policy-type access-control specific policy-map";
  }

  identity appnav {
    base policy-type;
    description
      "
       Policy-type APPNAV Policy Map";
  }

  identity control {
    base policy-type;
    description
      "
       Policy-type control policy-map";
  }

  identity inspect {
    base policy-type;
    description
      "
       Policy-type Firewall Policy Map";
  }

  identity packet-service {
    base policy-type;
    description
      "
       Policy-type Packet Service Policy Map";
  }

  identity service {
    base policy-type;
    description
      "
       Policy-type policymap service configuration";
  }

  identity class-type {
    description
      "
       This is identity of base class-type";
  }

  identity qos-class {
    base class-type;
    description
      "
       QOS class-map";
  }

  identity access-control-class {
    base class-type;
    description
      "
       Access-control specific class-map";
  }

  identity appnav-class {
    base class-type;
    description
      "
       APPNAV Class Map";
  }

  identity control-class {
    base class-type;
    description
      "
       Control policy class-map";
  }

  identity inspect-class {
    base class-type;
    description
      "
       Firewall Class Map";
  }

  typedef metric {
    type enumeration {
      enum none;
      enum peta;
      enum tera;
      enum giga;
      enum mega;
      enum kilo;
      enum milli;
      enum nano;
    }
    description
      "metric";
  }

  typedef rate-unit {
    type enumeration {
      enum pps;
      enum cps;
      enum bps;
      enum perc;
      enum ratio;
    }
    description
      "Unit for traffic rate:
       pps:     packets per sec
       cps:     cells per sec
       bps:     bits per sec
       perc:    percentage
       ratio:   ratio";
  }

  typedef direction {
    type enumeration {
      enum inbound;
      enum outbound;
    }
    description
      "
       This typedef defines directional enums used in c3pl.
       inbound:         Incoming direction.
       outbound:        Outgoing direction.
      ";
  }

  identity cos {
    base classifier:filter-type;
    description
      "
       Filter-type IEEE 802.1Q/ISL class of service/user
       priority values";
  }

  identity cos-inner {
    base classifier:filter-type;
    description
      "ATM VC configured as Access VC
       class of service/user priority values";
  }

  identity ipv4-acl-name {
    base classifier:filter-type;
    description
      "IPV4 access group list";
  }

  identity ipv6-acl-name {
    base classifier:filter-type;
    description
      "IPV6 access group list";
  }

  identity ipv4-acl {
    base classifier:filter-type;
    description
      "IPV4 access group Index";
  }

  identity ipv6-acl {
    base classifier:filter-type;
    description
      "IPV6 access group Index";
  }

  identity input-interface {
    base classifier:filter-type;
    description
      "Input interface";
  }

  identity src-mac {
    base classifier:filter-type;
    description
      "Source MAC address";
  }

  identity dst-mac {
    base classifier:filter-type;
    description
      "Destination MAC address";
  }

  identity mpls-exp-top {
    base classifier:filter-type;
    description
      "Multi Protocol Label Switching experimental
       topmost specific values";
  }

  identity mpls-exp-imp {
    base classifier:filter-type;
    description
      "Multi Protocol Label Switching experimental
       imposition specific values";
  }

  identity packet-length {
    base classifier:filter-type;
    description
      "Layer 3 packet length";
  }

  identity prec {
    base classifier:filter-type;
    description
      "IP precendence";
  }

  identity qos-group {
    base classifier:filter-type;
    description
      "QOS group";
  }

  identity vlan {
    base classifier:filter-type;
    description
      "Vlan";
  }

  identity vlan-inner {
    base classifier:filter-type;
    description
      "Vlan-inner";
  }

  identity atm-clp {
    base classifier:filter-type;
    description
      "ATM CLP bit";
  }

  identity atm-vci {
    base classifier:filter-type;
    description
      "ATM VCI number";
  }

  identity dei {
    base classifier:filter-type;
    description
      "Frame-relay DE bit";
  }

  identity dei-inner {
    base classifier:filter-type;
    description
      "Frame-relay inner DE bit";
  }

  identity flow-ip {
    base classifier:filter-type;
    description
      "Flow IP";
  }

  identity flow-record {
    base classifier:filter-type;
    description
      "FLow record";
  }

  identity flow-de {
    base classifier:filter-type;
    description
      "Flow DE";
  }

  identity flow-dlci {
    base classifier:filter-type;
    description
      "Frame-relay DLCI";
  }

  identity wlan-user-priority {
    base classifier:filter-type;
    description
      "WLAN user priority";
  }

  identity discard-class {
    base classifier:filter-type;
    description
      "Discard behavior identifier";
  }

  identity class-map {
    base classifier:filter-type;
    description
      "class-map";
  }

  identity metadata {
    base classifier:filter-type;
    description
      "metadata";
  }

  identity application {
    base classifier:filter-type;
    description
      "application";
  }

  identity security-group-name {
    base classifier:filter-type;
    description
      "security group name";
  }

  identity security-group-tag {
    base classifier:filter-type;
    description
      "security group tag";
  }

  identity ip-rtp {
    base classifier:filter-type;
    description
      "IP RTP port";
  }

  identity vpls {
    base classifier:filter-type;
    description
      "VPLS";
  }

  feature match-cos-support {
    description
      "Match COS feature support";
  }

  feature match-cos-inner-support {
    description
      "Match COS-inner feature support";
  }

  feature match-ipv4-acl-name-support {
    description
      "Match IPV4 ACL list feature support";
  }

  feature match-ipv6-acl-name-support {
    description
      "Match IPV6 ACL list feature support";
  }

  feature match-ipv4-acl-support {
    description
      "Match IPV4 ACL number feature support";
  }

  feature match-ipv6-acl-support {
    description
      "Match IPV6 ACL number feature support";
  }

  feature match-input-interface-support {
    description
      "Match input interface support";
  }

  feature match-src-mac-support {
    description
      "Match source Mac address feature support";
  }

  feature match-dst-mac-support {
    description
      "Match destination Mac address feature support";
  }

  feature protocol-name-support {
    description
      "Match non-standard protocol feature support";
  }

  feature match-packet-length-support {
    description
      "Match packet length feature support";
  }

  feature match-discard-class-support {
    description
      "Match discard class feature support";
  }

  feature match-class-map-support {
    description
      "Match class-map feature support";
  }

  feature match-qos-group-support {
    description
      "Match QOS group feature support";
  }

  feature match-prec-support {
    description
      "Match IP precendence feature support";
  }

  feature match-mpls-exp-imp-support {
    description
      "Match MPLS experimental imposition feature
       support";
  }

  feature match-mpls-exp-top-support {
    description
      "Match MPLS experimental topmost feature
       support";
  }

  feature match-fr-de-support {
    description
      "Match Frame relay DE feature support";
  }

  feature match-fr-dlci-support {
    description
      "Match Frame relay DLCI feature support";
  }

  feature match-atm-clp-support {
    description
      "Match ATM CLP feature support";
  }

  feature match-atm-vci-support {
    description
      "Match ATM VCI feature support";
  }

  feature match-vlan-inner-support {
    description
      "Match Vlan-inner feature support";
  }

  feature match-vlan-support {
    description
      "Match VLAN feature support";
  }

  feature match-dei-support {
    description
      "Match Frame relay DEI feature support";
  }

  feature match-dei-inner-support {
    description
      "Match Frame relay DEI inner feature support";
  }

  feature match-flow-ip-support {
    description
      "Match Flow IP feature support";
  }

  feature match-flow-record-support {
    description
      "Match Flow record feature support";
  }

  feature match-wlan-user-priority-support {
    description
      "Match Wlan user priority feature support";
  }

  feature match-metadata-support {
    description
      "Match Metadata feature support";
  }

  feature match-application-support {
    description
      "Match Application feature support";
  }

  feature match-security-group-support {
    description
      "Match Security group feature support";
  }

  feature match-ip-rtp-support {
    description
      "Match IP RTP feature support";
  }

  feature match-vpls-support {
    description
      "Match VPLS feature support";
  }

  typedef pkt-len-type {
    type uint16 {
      range "1..9216";
    }
    description
      "Layer 3 packet length from 1 to 9216";
  }

  typedef dscp-type {
    type inet:dscp;
    description
      "
       Differentiated services codepoint.
      ";
  }

  typedef src-dst-ip-type {
    type inet:ip-prefix;
    description
      "
       Source/destination IP prefix.";
  }

  typedef src-dst-port-type {
    type inet:port-number;
    description
      "Source/destination port value";
  }

  typedef protocol-type {
    type string;
    description
      "Name of the protocol";
  }

  typedef protocol-name {
    type string;
    description
      "Name of the protocol";
  }

  typedef cos-type {
    type uint8 {
      range "0..7";
    }
    description
      "
       Class of service.
      ";
  }

  typedef ip-acl-name-type {
    type string {
      length "1..64";
    }
    description
      "IPv4/6 access group.";
  }

  typedef ip-acl-type {
    type uint32;
    description
      "IPv4/6 access group number.";
  }

  typedef prec-val-type {
    type uint8 {
      range "0..7";
    }
    description
      "
       IP precendece value.
      ";
  }

  typedef prec-attr-type {
    type string;
    description
      "
       IP precendece attribute.";
  }

  typedef mpls-exp-type {
    type uint8 {
      range "0..7";
    }
    description
      "
       MPLS Experimental bits.
      ";
  }

  typedef discard-class-type {
    type uint8 {
      range "0..7";
    }
    description
      "
       Discard behavior identifier.
      ";
  }

  typedef dei-type {
    type boolean;
    description
      "
       Frame relay DEI.
      ";
  }

  typedef flow-record-type {
    type string {
      length "1..255";
    }
    description
      "
       Flow record.";
  }

  typedef fr-de-type {
    type empty;
    description
      "
       Frame relay DE type definition.";
  }

  typedef wlan-user-priority-type {
    type uint8 {
      range "0..7";
    }
    description
      "
       Wlan user priority value.";
  }

  typedef class-map-type {
    type string {
      length "1..64";
    }
    description
      "
       Class-map name.";
  }

  typedef application-type {
    type string;
    description
      "
       Application name.";
  }

  typedef qos-group-type {
    type uint16 {
      range "0..99";
    }
    description
      "
       QoS Group value.
      ";
  }

  typedef vlan-type {
    type uint16 {
      range "1..4095";
    }
    description
      "
       Vlan ID.
      ";
  }
}
