/*
 * Generated by confdc --mib2yang-std
 * Source: mgmt/dmi/model/mib/src/MPLS-L3VPN-STD-MIB.mib
 */
/*
 * This YANG module has been generated by smidump 0.5.0:
 *
 *      smidump -f yang MPLS-L3VPN-STD-MIB
 *
 * Do not edit. Edit the source file instead!
 */

module MPLS-L3VPN-STD-MIB {

  namespace "urn:ietf:params:xml:ns:yang:smiv2:MPLS-L3VPN-STD-MIB";
  prefix MPLS-L3VPN-STD-MIB;

  import IANA-RTPROTO-MIB {
    prefix "iana-rtproto";
  }

  import IF-MIB {
    prefix "if-mib";
  }

  import INET-ADDRESS-MIB {
    prefix "inet-address";
  }

  import MPLS-LSR-STD-MIB {
    prefix "mpls-lsr";
  }

  import SNMP-FRAMEWORK-MIB {
    prefix "snmp-framework";
  }

  import SNMPv2-TC {
    prefix "snmpv2-tc";
  }

  import VPN-TC-STD-MIB {
    prefix "vpn-tc";
  }

  import ietf-inet-types {
    prefix "inet";
  }

  import ietf-yang-smiv2 {
    prefix "smiv2";
  }

  import ietf-yang-types {
    prefix "yang";
  }

  organization
   "IETF Layer-3 Virtual Private
    Networks Working Group.";

  contact
   "        Thomas D. Nadeau
    tnadeau@cisco.com
    
    Harmen van der Linde
    havander@cisco.com
    
    Comments and discussion to l3vpn@ietf.org";

  description
   "This MIB contains managed object definitions for the
    Layer-3 Multiprotocol Label Switching Virtual
    Private Networks.
    
    Copyright (C) The Internet Society (2006).  This
    version of this MIB module is part of RFC4382; see
    the RFC itself for full legal notices.";

  revision 2006-01-23 {
    description
     "Initial version.  Published as RFC 4382.";
  }

  typedef MplsL3VpnName {
    type binary {
      length "0..31";
    }
    description
     "An identifier that is assigned to each MPLS/BGP VPN and
      is used to uniquely identify it.  This is assigned by the
      system operator or NMS and SHOULD be unique throughout
      the MPLS domain.  If this is the case, then this identifier
      can then be used at any LSR within a specific MPLS domain
      to identify this MPLS/BGP VPN.  It may also be possible to
      preserve the uniqueness of this identifier across MPLS
      domain boundaries, in which case this identifier can then
      be used to uniquely identify MPLS/BGP VPNs on a more global
      basis.  This object MAY be set to the VPN ID as defined in
      RFC 2685.";
    reference
     "RFC 2685 Fox B., et al, 'Virtual Private
      
      Networks Identifier', September 1999.";
  }

  typedef MplsL3VpnRouteDistinguisher {
    type binary {
      length "0..256";
    }
    description
     "Syntax for a route distinguisher and route target
      as defined in [RFC4364].";
    reference
     "[RFC4364]";
  }

  typedef MplsL3VpnRtType {
    type enumeration {
      enum "import" {
        value "1";
      }
      enum "export" {
        value "2";
      }
      enum "both" {
        value "3";
      }
    }
    description
     "Used to define the type of a route target usage.
      Route targets can be specified to be imported,
      exported, or both.  For a complete definition of a
      route target, see [RFC4364].";
    reference
     "[RFC4364]";
  }


  container MPLS-L3VPN-STD-MIB {
    config false;

    container mplsL3VpnScalars {
      smiv2:oid "1.3.6.1.2.1.10.166.11.1.1";

      leaf mplsL3VpnConfiguredVrfs {
        type uint32;
        description
         "The number of VRFs that are configured on this node.";
        smiv2:max-access "read-only";
        smiv2:oid "1.3.6.1.2.1.10.166.11.1.1.1";
      }

      leaf mplsL3VpnActiveVrfs {
        type yang:gauge32;
        description
         "The number of VRFs that are active on this node.
          That is, those VRFs whose corresponding mplsL3VpnVrfOperStatus
          object value is equal to operational (1).";
        smiv2:max-access "read-only";
        smiv2:oid "1.3.6.1.2.1.10.166.11.1.1.2";
      }

      leaf mplsL3VpnConnectedInterfaces {
        type yang:gauge32;
        description
         "Total number of interfaces connected to a VRF.";
        smiv2:max-access "read-only";
        smiv2:oid "1.3.6.1.2.1.10.166.11.1.1.3";
      }

      leaf mplsL3VpnNotificationEnable {
        type boolean;
        description
         "If this object is true, then it enables the
          generation of all notifications defined in
          this MIB.  This object's value should be
          preserved across agent reboots.";
        reference
         "See also [RFC3413] for explanation that
          notifications are under the ultimate control of the
          MIB modules in this document.";
        smiv2:defval "false";
        smiv2:max-access "read-write";
        smiv2:oid "1.3.6.1.2.1.10.166.11.1.1.4";
      }

      leaf mplsL3VpnVrfConfMaxPossRts {
        type uint32;
        description
         "Denotes maximum number of routes that the device
          will allow all VRFs jointly to hold.  If this value is
          set to 0, this indicates that the device is
          unable to determine the absolute maximum.  In this
          case, the configured maximum MAY not actually
          be allowed by the device.";
        smiv2:max-access "read-only";
        smiv2:oid "1.3.6.1.2.1.10.166.11.1.1.5";
      }

      leaf mplsL3VpnVrfConfRteMxThrshTime {
        type uint32;
        units "seconds";
        description
         "Denotes the interval in seconds, at which the route max threshold
          notification may be reissued after the maximum value has been
          exceeded (or has been reached if mplsL3VpnVrfConfMaxRoutes and
          mplsL3VpnVrfConfHighRteThresh are equal) and the initial
          notification has been issued.  This value is intended to prevent
          continuous generation of notifications by an agent in the event
          that routes are continually added to a VRF after it has reached
          its maximum value.  If this value is set to 0, the agent should
          only issue a single notification at the time that the maximum
          threshold has been reached, and should not issue any more
          notifications until the value of routes has fallen below the
          configured threshold value.  This is the recommended default
          behavior.";
        smiv2:defval "0";
        smiv2:max-access "read-only";
        smiv2:oid "1.3.6.1.2.1.10.166.11.1.1.6";
      }

      leaf mplsL3VpnIllLblRcvThrsh {
        type uint32;
        description
         "The number of illegally received labels above which
          the mplsNumVrfSecIllglLblThrshExcd notification
          is issued.  The persistence of this value mimics
          that of the device's configuration.";
        smiv2:max-access "read-write";
        smiv2:oid "1.3.6.1.2.1.10.166.11.1.1.7";
      }
    }

    container mplsL3VpnIfConfTable {
      description
       "This table specifies per-interface MPLS capability
        and associated information.";
      smiv2:oid "1.3.6.1.2.1.10.166.11.1.2.1";

      list mplsL3VpnIfConfEntry {
        key "mplsL3VpnVrfName mplsL3VpnIfConfIndex";
        description
         "An entry in this table is created by an LSR for
          every interface capable of supporting MPLS L3VPN.
          Each entry in this table is meant to correspond to
          an entry in the Interfaces Table.";
        smiv2:oid "1.3.6.1.2.1.10.166.11.1.2.1.1";

        leaf mplsL3VpnVrfName {
          type leafref {
            path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
          }
        }

        leaf mplsL3VpnIfConfIndex {
          type if-mib:InterfaceIndex;
          description
           "This is a unique index for an entry in the
            mplsL3VpnIfConfTable.  A non-zero index for an
            entry indicates the ifIndex for the corresponding
            interface entry in the MPLS-VPN-layer in the ifTable.
            Note that this table does not necessarily correspond
            one-to-one with all entries in the Interface MIB
            having an ifType of MPLS-layer; rather, only those
            that are enabled for MPLS L3VPN functionality.";
          reference
           "RFC2863";
          smiv2:max-access "not-accessible";
          smiv2:oid "1.3.6.1.2.1.10.166.11.1.2.1.1.1";
        }

        leaf mplsL3VpnIfVpnClassification {
          type enumeration {
            enum "carrierOfCarrier" {
              value "1";
            }
            enum "enterprise" {
              value "2";
            }
            enum "interProvider" {
              value "3";
            }
          }
          description
           "Denotes whether this link participates in a
            carrier's carrier, enterprise, or inter-provider
            scenario.";
          smiv2:defval "enterprise";
          smiv2:max-access "read-write";
          smiv2:oid "1.3.6.1.2.1.10.166.11.1.2.1.1.2";
        }

        leaf mplsL3VpnIfVpnRouteDistProtocol {
          type bits {
            bit none {
              position "0";
            }
            bit bgp {
              position "1";
            }
            bit ospf {
              position "2";
            }
            bit rip {
              position "3";
            }
            bit isis {
              position "4";
            }
            bit static {
              position "5";
            }
            bit other {
              position "6";
            }
          }
          description
           "Denotes the route distribution protocol across the
            PE-CE link.  Note that more than one routing protocol
            may be enabled at the same time; thus, this object is
            specified as a bitmask.  For example, static(5) and
            ospf(2) are a typical configuration.";
          smiv2:max-access "read-write";
          smiv2:oid "1.3.6.1.2.1.10.166.11.1.2.1.1.3";
        }

        leaf mplsL3VpnIfConfStorageType {
          type snmpv2-tc:StorageType;
          description
           "The storage type for this VPN If entry.
            Conceptual rows having the value 'permanent'
            need not allow write access to any columnar
            objects in the row.";
          reference
           "See RFC2579.";
          smiv2:defval "volatile";
          smiv2:max-access "read-write";
          smiv2:oid "1.3.6.1.2.1.10.166.11.1.2.1.1.4";
        }

        leaf mplsL3VpnIfConfRowStatus {
          type snmpv2-tc:RowStatus;
          description
           "This variable is used to create, modify, and/or
            delete a row in this table.  Rows in this
            table signify that the specified interface is
            associated with this VRF.  If the row creation
            operation succeeds, the interface will have been
            associated with the specified VRF, otherwise the
            agent MUST not allow the association.  If the agent
            only allows read-only operations on this table, it
            MUST create entries in this table as they are created
            on the device.  When a row in this table is in
            active(1) state, no objects in that row can be
            modified except mplsL3VpnIfConfStorageType and
            mplsL3VpnIfConfRowStatus.";
          smiv2:max-access "read-write";
          smiv2:oid "1.3.6.1.2.1.10.166.11.1.2.1.1.5";
        }
      }
    }

    container mplsL3VpnVrfTable {
      description
       "This table specifies per-interface MPLS L3VPN
        VRF Table capability and associated information.
        Entries in this table define VRF routing instances
        associated with MPLS/VPN interfaces.  Note that
        multiple interfaces can belong to the same VRF
        instance.  The collection of all VRF instances
        comprises an actual VPN.";
      smiv2:oid "1.3.6.1.2.1.10.166.11.1.2.2";

      list mplsL3VpnVrfEntry {
        key "mplsL3VpnVrfName";
        description
         "An entry in this table is created by an LSR for
          every VRF capable of supporting MPLS L3VPN.  The
          indexing provides an ordering of VRFs per-VPN
          interface.";
        smiv2:oid "1.3.6.1.2.1.10.166.11.1.2.2.1";

        leaf mplsL3VpnVrfName {
          type MPLS-L3VPN-STD-MIB:MplsL3VpnName;
          description
           "The human-readable name of this VPN.  This MAY
            be equivalent to the [RFC2685] VPN-ID, but may
            also vary.  If it is set to the VPN ID, it MUST
            be equivalent to the value of mplsL3VpnVrfVpnId.
            It is strongly recommended that all sites supporting
            VRFs that are part of the same VPN use the same
            naming convention for VRFs as well as the same VPN
            ID.";
          reference
           "[RFC2685]";
          smiv2:max-access "not-accessible";
          smiv2:oid "1.3.6.1.2.1.10.166.11.1.2.2.1.1";
        }

        leaf mplsL3VpnVrfVpnId {
          type vpn-tc:VPNIdOrZero;
          description
           "The VPN ID as specified in [RFC2685].  If a VPN ID
            has not been specified for this VRF, then this
            variable SHOULD be set to a zero-length OCTET
            STRING.";
          smiv2:max-access "read-write";
          smiv2:oid "1.3.6.1.2.1.10.166.11.1.2.2.1.2";
        }

        leaf mplsL3VpnVrfDescription {
          type snmp-framework:SnmpAdminString;
          description
           "The human-readable description of this VRF.";
          smiv2:defval "";
          smiv2:max-access "read-write";
          smiv2:oid "1.3.6.1.2.1.10.166.11.1.2.2.1.3";
        }

        leaf mplsL3VpnVrfRD {
          type MPLS-L3VPN-STD-MIB:MplsL3VpnRouteDistinguisher;
          description
           "The route distinguisher for this VRF.";
          smiv2:defval "";
          smiv2:max-access "read-write";
          smiv2:oid "1.3.6.1.2.1.10.166.11.1.2.2.1.4";
        }

        leaf mplsL3VpnVrfCreationTime {
          type yang:timestamp;
          description
           "The time at which this VRF entry was created.";
          smiv2:max-access "read-only";
          smiv2:oid "1.3.6.1.2.1.10.166.11.1.2.2.1.5";
        }

        leaf mplsL3VpnVrfOperStatus {
          type enumeration {
            enum "up" {
              value "1";
            }
            enum "down" {
              value "2";
            }
          }
          description
           "Denotes whether or not a VRF is operational.  A VRF is
            up(1) when there is at least one interface associated
            with the VRF whose ifOperStatus is up(1).  A VRF is
            down(2) when:
            a. There does not exist at least one interface whose
               ifOperStatus is up(1).
            b. There are no interfaces associated with the VRF.";
          smiv2:max-access "read-only";
          smiv2:oid "1.3.6.1.2.1.10.166.11.1.2.2.1.6";
        }

        leaf mplsL3VpnVrfActiveInterfaces {
          type yang:gauge32;
          description
           "Total number of interfaces connected to this VRF with
            ifOperStatus = up(1).
            
            This value should increase when an interface is associated
            with the corresponding VRF and its corresponding ifOperStatus
            is equal to up(1).  If an interface is associated whose
            ifOperStatus is not up(1), then the value is not incremented
            until such time as it transitions to this state.
            
            This value should be decremented when an interface is
            disassociated with a VRF or the corresponding ifOperStatus
            transitions out of the up(1) state to any other state.";
          smiv2:max-access "read-only";
          smiv2:oid "1.3.6.1.2.1.10.166.11.1.2.2.1.7";
        }

        leaf mplsL3VpnVrfAssociatedInterfaces {
          type uint32;
          description
           "Total number of interfaces connected to this VRF
            (independent of ifOperStatus type).";
          smiv2:max-access "read-only";
          smiv2:oid "1.3.6.1.2.1.10.166.11.1.2.2.1.8";
        }

        leaf mplsL3VpnVrfConfMidRteThresh {
          type uint32;
          description
           "Denotes mid-level water marker for the number
            of routes that this VRF may hold.";
          smiv2:defval "0";
          smiv2:max-access "read-write";
          smiv2:oid "1.3.6.1.2.1.10.166.11.1.2.2.1.9";
        }

        leaf mplsL3VpnVrfConfHighRteThresh {
          type uint32;
          description
           "Denotes high-level water marker for the number of
            routes that this VRF may hold.";
          smiv2:defval "0";
          smiv2:max-access "read-write";
          smiv2:oid "1.3.6.1.2.1.10.166.11.1.2.2.1.10";
        }

        leaf mplsL3VpnVrfConfMaxRoutes {
          type uint32;
          description
           "Denotes maximum number of routes that this VRF is
            configured to hold.  This value MUST be less than or
            equal to mplsL3VpnVrfConfMaxPossRts unless it is set
            to 0.";
          smiv2:defval "0";
          smiv2:max-access "read-write";
          smiv2:oid "1.3.6.1.2.1.10.166.11.1.2.2.1.11";
        }

        leaf mplsL3VpnVrfConfLastChanged {
          type yang:timestamp;
          description
           "The value of sysUpTime at the time of the last
            change of this table entry, which includes changes of
            VRF parameters defined in this table or addition or
            deletion of interfaces associated with this VRF.";
          smiv2:max-access "read-only";
          smiv2:oid "1.3.6.1.2.1.10.166.11.1.2.2.1.12";
        }

        leaf mplsL3VpnVrfConfRowStatus {
          type snmpv2-tc:RowStatus;
          description
           "This variable is used to create, modify, and/or
            delete a row in this table.
            
            When a row in this table is in active(1) state, no
            objects in that row can be modified except
            mplsL3VpnVrfConfAdminStatus, mplsL3VpnVrfConfRowStatus,
            and mplsL3VpnVrfConfStorageType.";
          smiv2:max-access "read-write";
          smiv2:oid "1.3.6.1.2.1.10.166.11.1.2.2.1.13";
        }

        leaf mplsL3VpnVrfConfAdminStatus {
          type enumeration {
            enum "up" {
              value "1";
            }
            enum "down" {
              value "2";
            }
            enum "testing" {
              value "3";
            }
          }
          description
           "Indicates the desired operational status of this
            VRF.";
          smiv2:max-access "read-write";
          smiv2:oid "1.3.6.1.2.1.10.166.11.1.2.2.1.14";
        }

        leaf mplsL3VpnVrfConfStorageType {
          type snmpv2-tc:StorageType;
          description
           "The storage type for this VPN VRF entry.
            Conceptual rows having the value 'permanent'
            need not allow write access to any columnar
            objects in the row.";
          reference
           "See RFC2579.";
          smiv2:defval "volatile";
          smiv2:max-access "read-write";
          smiv2:oid "1.3.6.1.2.1.10.166.11.1.2.2.1.15";
        }
      }
    }

    container mplsL3VpnVrfRTTable {
      description
       "This table specifies per-VRF route target association.
        Each entry identifies a connectivity policy supported
        as part of a VPN.";
      smiv2:oid "1.3.6.1.2.1.10.166.11.1.2.3";

      list mplsL3VpnVrfRTEntry {
        key "mplsL3VpnVrfName mplsL3VpnVrfRTIndex mplsL3VpnVrfRTType";
        description
         "An entry in this table is created by an LSR for
          each route target configured for a VRF supporting
          a MPLS L3VPN instance.  The indexing provides an
          ordering per-VRF instance.  See [RFC4364] for a
          complete definition of a route target.";
        smiv2:oid "1.3.6.1.2.1.10.166.11.1.2.3.1";

        leaf mplsL3VpnVrfName {
          type leafref {
            path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
          }
        }

        leaf mplsL3VpnVrfRTIndex {
          type uint32 {
            range "1..4294967295";
          }
          description
           "Auxiliary index for route targets configured for a
            particular VRF.";
          smiv2:max-access "not-accessible";
          smiv2:oid "1.3.6.1.2.1.10.166.11.1.2.3.1.2";
        }

        leaf mplsL3VpnVrfRTType {
          type MPLS-L3VPN-STD-MIB:MplsL3VpnRtType;
          description
           "The route target distribution type.";
          smiv2:max-access "not-accessible";
          smiv2:oid "1.3.6.1.2.1.10.166.11.1.2.3.1.3";
        }

        leaf mplsL3VpnVrfRT {
          type MPLS-L3VPN-STD-MIB:MplsL3VpnRouteDistinguisher;
          description
           "The route target distribution policy.";
          smiv2:defval "";
          smiv2:max-access "read-write";
          smiv2:oid "1.3.6.1.2.1.10.166.11.1.2.3.1.4";
        }

        leaf mplsL3VpnVrfRTDescr {
          type snmp-framework:SnmpAdminString;
          description
           "Description of the route target.";
          smiv2:defval "";
          smiv2:max-access "read-write";
          smiv2:oid "1.3.6.1.2.1.10.166.11.1.2.3.1.5";
        }

        leaf mplsL3VpnVrfRTRowStatus {
          type snmpv2-tc:RowStatus;
          description
           "This variable is used to create, modify, and/or
            delete a row in this table.  When a row in this
            table is in active(1) state, no objects in that row
            can be modified except mplsL3VpnVrfRTRowStatus.";
          smiv2:max-access "read-write";
          smiv2:oid "1.3.6.1.2.1.10.166.11.1.2.3.1.6";
        }

        leaf mplsL3VpnVrfRTStorageType {
          type snmpv2-tc:StorageType;
          description
           "The storage type for this VPN route target (RT) entry.
            Conceptual rows having the value 'permanent'
            need not allow write access to any columnar
            objects in the row.";
          reference
           "See RFC2579.";
          smiv2:defval "volatile";
          smiv2:max-access "read-write";
          smiv2:oid "1.3.6.1.2.1.10.166.11.1.2.3.1.7";
        }
      }
    }

    container mplsL3VpnVrfRteTable {
      description
       "This table specifies per-interface MPLS L3VPN VRF Table
        routing information.  Entries in this table define VRF routing
        entries associated with the specified MPLS/VPN interfaces.  Note
        
        that this table contains both BGP and Interior Gateway Protocol
        IGP routes, as both may appear in the same VRF.";
      reference
       "[RFC2096]";
      smiv2:oid "1.3.6.1.2.1.10.166.11.1.4.1";

      list mplsL3VpnVrfRteEntry {
        key "mplsL3VpnVrfName mplsL3VpnVrfRteInetCidrDestType mplsL3VpnVrfRteInetCidrDest mplsL3VpnVrfRteInetCidrPfxLen mplsL3VpnVrfRteInetCidrPolicy mplsL3VpnVrfRteInetCidrNHopType mplsL3VpnVrfRteInetCidrNextHop";
        description
         "An entry in this table is created by an LSR for every route
          present configured (either dynamically or statically) within
          the context of a specific VRF capable of supporting MPLS/BGP
          VPN.  The indexing provides an ordering of VRFs per-VPN
          interface.
          
          Implementers need to be aware that there are quite a few
          index objects that together can exceed the size allowed
          for an Object Identifier (OID).  So implementers must make
          sure that OIDs of column instances in this table will have
          no more than 128 sub-identifiers, otherwise they cannot be
          accessed using SNMPv1, SNMPv2c, or SNMPv3.";
        smiv2:oid "1.3.6.1.2.1.10.166.11.1.4.1.1";

        leaf mplsL3VpnVrfName {
          type leafref {
            path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
          }
        }

        leaf mplsL3VpnVrfRteInetCidrDestType {
          type inet-address:InetAddressType;
          description
           "The type of the mplsL3VpnVrfRteInetCidrDest address, as
            defined in the InetAddress MIB.
            
            Only those address types that may appear in an actual
            routing table are allowed as values of this object.";
          reference
           "RFC4001";
          smiv2:max-access "not-accessible";
          smiv2:oid "1.3.6.1.2.1.10.166.11.1.4.1.1.1";
        }

        leaf mplsL3VpnVrfRteInetCidrDest {
          type inet-address:InetAddress;
          description
           "The destination IP address of this route.
            
            The type of this address is determined by the value of
            the mplsL3VpnVrfRteInetCidrDestType object.
            
            The values for the index objects
            mplsL3VpnVrfRteInetCidrDest and
            mplsL3VpnVrfRteInetCidrPfxLen must be consistent.  When
            the value of mplsL3VpnVrfRteInetCidrDest is x, then
            the bitwise logical-AND of x with the value of the mask
            formed from the corresponding index object
            mplsL3VpnVrfRteInetCidrPfxLen MUST be
            equal to x.  If not, then the index pair is not
            consistent and an inconsistentName error must be
            returned on SET or CREATE requests.";
          smiv2:max-access "not-accessible";
          smiv2:oid "1.3.6.1.2.1.10.166.11.1.4.1.1.2";
        }

        leaf mplsL3VpnVrfRteInetCidrPfxLen {
          type inet-address:InetAddressPrefixLength {
            range "0..128";
          }
          description
           "Indicates the number of leading one bits that form the
            
            mask to be logical-ANDed with the destination address
            before being compared to the value in the
            mplsL3VpnVrfRteInetCidrDest field.
            
            The values for the index objects
            mplsL3VpnVrfRteInetCidrDest and
            mplsL3VpnVrfRteInetCidrPfxLen must be consistent.  When
            the value of mplsL3VpnVrfRteInetCidrDest is x, then the
            bitwise logical-AND of x with the value of the mask
            formed from the corresponding index object
            mplsL3VpnVrfRteInetCidrPfxLen MUST be
            equal to x.  If not, then the index pair is not
            consistent and an inconsistentName error must be
            returned on SET or CREATE requests.";
          smiv2:max-access "not-accessible";
          smiv2:oid "1.3.6.1.2.1.10.166.11.1.4.1.1.3";
        }

        leaf mplsL3VpnVrfRteInetCidrPolicy {
          type yang:object-identifier-128;
          description
           "This object is an opaque object without any defined
            semantics.  Its purpose is to serve as an additional
            index that may delineate between multiple entries to
            the same destination.  The value { 0 0 } shall be used
            as the default value for this object.";
          smiv2:max-access "not-accessible";
          smiv2:oid "1.3.6.1.2.1.10.166.11.1.4.1.1.4";
        }

        leaf mplsL3VpnVrfRteInetCidrNHopType {
          type inet-address:InetAddressType;
          description
           "The type of the mplsL3VpnVrfRteInetCidrNextHop address,
            as defined in the InetAddress MIB.
            
            Value should be set to unknown(0) for non-remote
            routes.
            
            Only those address types that may appear in an actual
            routing table are allowed as values of this object.";
          reference
           "RFC4001";
          smiv2:max-access "not-accessible";
          smiv2:oid "1.3.6.1.2.1.10.166.11.1.4.1.1.5";
        }

        leaf mplsL3VpnVrfRteInetCidrNextHop {
          type inet-address:InetAddress;
          description
           "On remote routes, the address of the next system en
            route.  For non-remote routes, a zero-length string.
            The type of this address is determined by the value of
            the mplsL3VpnVrfRteInetCidrNHopType object.";
          smiv2:max-access "not-accessible";
          smiv2:oid "1.3.6.1.2.1.10.166.11.1.4.1.1.6";
        }

        leaf mplsL3VpnVrfRteInetCidrIfIndex {
          type if-mib:InterfaceIndexOrZero;
          description
           "The ifIndex value that identifies the local interface
            through which the next hop of this route should be
            reached.  A value of 0 is valid and represents the
            scenario where no interface is specified.";
          smiv2:defval "0";
          smiv2:max-access "read-write";
          smiv2:oid "1.3.6.1.2.1.10.166.11.1.4.1.1.7";
        }

        leaf mplsL3VpnVrfRteInetCidrType {
          type enumeration {
            enum "other" {
              value "1";
            }
            enum "reject" {
              value "2";
            }
            enum "local" {
              value "3";
            }
            enum "remote" {
              value "4";
            }
            enum "blackhole" {
              value "5";
            }
          }
          description
           "The type of route.  Note that local(3) refers to a
            route for which the next hop is the final destination;
            remote(4) refers to a route for which the next hop is
            not the final destination.
            
            Routes that do not result in traffic forwarding or
            rejection should not be displayed even if the
            implementation keeps them stored internally.
            
            reject(2) refers to a route that, if matched, discards
            the message as unreachable and returns a notification
            (e.g., ICMP error) to the message sender.  This is used
            in some protocols as a means of correctly aggregating
            routes.
            
            blackhole(5) refers to a route that, if matched,
            discards the message silently.";
          smiv2:defval "other";
          smiv2:max-access "read-write";
          smiv2:oid "1.3.6.1.2.1.10.166.11.1.4.1.1.8";
        }

        leaf mplsL3VpnVrfRteInetCidrProto {
          type iana-rtproto:IANAipRouteProtocol;
          description
           "The routing mechanism via which this route was learned.
            Inclusion of values for gateway routing protocols is
            not intended to imply that hosts should support those
            protocols.";
          smiv2:max-access "read-only";
          smiv2:oid "1.3.6.1.2.1.10.166.11.1.4.1.1.9";
        }

        leaf mplsL3VpnVrfRteInetCidrAge {
          type yang:gauge32;
          description
           "The number of seconds since this route was last updated
            or otherwise determined to be correct.  Note that no
            semantics of 'too old' can be implied except through
            knowledge of the routing protocol by which the route
            was learned.";
          smiv2:max-access "read-only";
          smiv2:oid "1.3.6.1.2.1.10.166.11.1.4.1.1.10";
        }

        leaf mplsL3VpnVrfRteInetCidrNextHopAS {
          type inet:as-number;
          description
           "The Autonomous System Number of the next hop.  The
            semantics of this object are determined by the
            routing protocol specified in the route's
            mplsL3VpnVrfRteInetCidrProto value.  When this
            object is unknown or not relevant, its value should
            be set to zero.";
          smiv2:defval "0";
          smiv2:max-access "read-write";
          smiv2:oid "1.3.6.1.2.1.10.166.11.1.4.1.1.11";
        }

        leaf mplsL3VpnVrfRteInetCidrMetric1 {
          type int32 {
            range "-1..2147483647";
          }
          description
           "The primary routing metric for this route.  The
            semantics of this metric are determined by the
            
            routing protocol specified in the route's
            mplsL3VpnVrfRteInetCidrProto value.  If this
            metric is not used, its value should be set to
            -1.";
          smiv2:defval "-1";
          smiv2:max-access "read-write";
          smiv2:oid "1.3.6.1.2.1.10.166.11.1.4.1.1.12";
        }

        leaf mplsL3VpnVrfRteInetCidrMetric2 {
          type int32 {
            range "-1..2147483647";
          }
          description
           "An alternate routing metric for this route.  The
            semantics of this metric are determined by the routing
            protocol specified in the route's
            mplsL3VpnVrfRteInetCidrProto
            value.  If this metric is not used, its value should be
            set to -1.";
          smiv2:defval "-1";
          smiv2:max-access "read-write";
          smiv2:oid "1.3.6.1.2.1.10.166.11.1.4.1.1.13";
        }

        leaf mplsL3VpnVrfRteInetCidrMetric3 {
          type int32 {
            range "-1..2147483647";
          }
          description
           "An alternate routing metric for this route.  The
            semantics of this metric are determined by the routing
            protocol specified in the route's
            mplsL3VpnVrfRteInetCidrProto
            value.  If this metric is not used, its value should be
            set to -1.";
          smiv2:defval "-1";
          smiv2:max-access "read-write";
          smiv2:oid "1.3.6.1.2.1.10.166.11.1.4.1.1.14";
        }

        leaf mplsL3VpnVrfRteInetCidrMetric4 {
          type int32 {
            range "-1..2147483647";
          }
          description
           "An alternate routing metric for this route.  The
            semantics of this metric are determined by the routing
            protocol specified in the route's
            mplsL3VpnVrfRteInetCidrProto value.  If this metric
            is not used, its value should be set to -1.";
          smiv2:defval "-1";
          smiv2:max-access "read-write";
          smiv2:oid "1.3.6.1.2.1.10.166.11.1.4.1.1.15";
        }

        leaf mplsL3VpnVrfRteInetCidrMetric5 {
          type int32 {
            range "-1..2147483647";
          }
          description
           "An alternate routing metric for this route.  The
            semantics of this metric are determined by the routing
            protocol specified in the route's
            mplsL3VpnVrfRteInetCidrProto value.  If this metric is
            not used, its value should be set to -1.";
          smiv2:defval "-1";
          smiv2:max-access "read-write";
          smiv2:oid "1.3.6.1.2.1.10.166.11.1.4.1.1.16";
        }

        leaf mplsL3VpnVrfRteXCPointer {
          type mpls-lsr:MplsIndexType;
          description
           "Index into mplsXCTable that identifies which cross-
            connect entry is associated with this VRF route entry
            by containing the mplsXCIndex of that cross-connect entry.
            The string containing the single-octet 0x00 indicates that
            a label stack is not associated with this route entry.  This
            can be the case because the label bindings have not yet
            been established, or because some change in the agent has
            removed them.
            
            When the label stack associated with this VRF route is created,
            it MUST establish the associated cross-connect
            entry in the mplsXCTable and then set that index to the value
            of this object.  Changes to the cross-connect object in the
            mplsXCTable MUST automatically be reflected in the value of
            this object.  If this object represents a static routing entry,
            then the manager must ensure that this entry is maintained
            consistently in the corresponding mplsXCTable as well.";
          reference
           "RFC 3813 - Multiprotocol Label Switching (MPLS) Label Switching
            Router (LSR) Management Information base (MIB), C. Srinivasan,
            A. Vishwanathan, and T. Nadeau, June 2004";
          smiv2:max-access "read-write";
          smiv2:oid "1.3.6.1.2.1.10.166.11.1.4.1.1.17";
        }

        leaf mplsL3VpnVrfRteInetCidrStatus {
          type snmpv2-tc:RowStatus;
          description
           "The row status variable, used according to row
            installation and removal conventions.
            
            A row entry cannot be modified when the status is
            marked as active(1).";
          smiv2:max-access "read-write";
          smiv2:oid "1.3.6.1.2.1.10.166.11.1.4.1.1.18";
        }
      }
    }
  }

  smiv2:alias "mplsL3VpnVrfSecTable" {
    description
     "This table specifies per MPLS L3VPN VRF Table
      security-related counters.";
    smiv2:oid "1.3.6.1.2.1.10.166.11.1.2.6";
  }

  smiv2:alias "mplsL3VpnVrfSecEntry" {
    description
     "An entry in this table is created by an LSR for
      every VRF capable of supporting MPLS L3VPN.  Each
      entry in this table is used to indicate security-related
      information for each VRF entry.";
    smiv2:oid "1.3.6.1.2.1.10.166.11.1.2.6.1";
  }

  augment "/MPLS-L3VPN-STD-MIB:MPLS-L3VPN-STD-MIB/MPLS-L3VPN-STD-MIB:mplsL3VpnVrfTable/MPLS-L3VPN-STD-MIB:mplsL3VpnVrfEntry" {
    description
     "An entry in this table is created by an LSR for
      every VRF capable of supporting MPLS L3VPN.  Each
      entry in this table is used to indicate security-related
      information for each VRF entry.";
    smiv2:oid "1.3.6.1.2.1.10.166.11.1.2.6.1";

    leaf mplsL3VpnVrfSecIllegalLblVltns {
      type yang:counter32;
      description
       "Indicates the number of illegally received
        labels on this VPN/VRF.
        
        Discontinuities in the value of this counter can occur
        at re-initialization of the management system, and at
        other times as indicated by the value of
        mplsL3VpnVrfSecDiscontinuityTime.";
      smiv2:max-access "read-only";
      smiv2:oid "1.3.6.1.2.1.10.166.11.1.2.6.1.1";
    }

    leaf mplsL3VpnVrfSecDiscontinuityTime {
      type yang:timestamp;
      description
       "The value of sysUpTime on the most recent occasion at
        which any one or more of this entry's counters suffered
        a discontinuity.  If no such discontinuities have
        occurred since the last re-initialization of the local
        management subsystem, then this object contains a zero
        value.";
      smiv2:max-access "read-only";
      smiv2:oid "1.3.6.1.2.1.10.166.11.1.2.6.1.2";
    }
  }

  smiv2:alias "mplsL3VpnVrfPerfTable" {
    description
     "This table specifies per MPLS L3VPN VRF Table performance
      
      information.";
    smiv2:oid "1.3.6.1.2.1.10.166.11.1.3.1";
  }

  smiv2:alias "mplsL3VpnVrfPerfEntry" {
    description
     "An entry in this table is created by an LSR for
      every VRF capable of supporting MPLS L3VPN.";
    smiv2:oid "1.3.6.1.2.1.10.166.11.1.3.1.1";
  }

  augment "/MPLS-L3VPN-STD-MIB:MPLS-L3VPN-STD-MIB/MPLS-L3VPN-STD-MIB:mplsL3VpnVrfTable/MPLS-L3VPN-STD-MIB:mplsL3VpnVrfEntry" {
    description
     "An entry in this table is created by an LSR for
      every VRF capable of supporting MPLS L3VPN.";
    smiv2:oid "1.3.6.1.2.1.10.166.11.1.3.1.1";

    leaf mplsL3VpnVrfPerfRoutesAdded {
      type yang:counter32;
      description
       "Indicates the number of routes added to this VPN/VRF
        since the last discontinuity.  Discontinuities in
        the value of this counter can occur
        at re-initialization of the management system, and at
        other times as indicated by the value of
        mplsL3VpnVrfPerfDiscTime.";
      smiv2:max-access "read-only";
      smiv2:oid "1.3.6.1.2.1.10.166.11.1.3.1.1.1";
    }

    leaf mplsL3VpnVrfPerfRoutesDeleted {
      type yang:counter32;
      description
       "Indicates the number of routes removed from this VPN/VRF.
        
        Discontinuities in the value of this counter can occur
        at re-initialization of the management system, and at
        other times as indicated by the value of
        mplsL3VpnVrfPerfDiscTime.";
      smiv2:max-access "read-only";
      smiv2:oid "1.3.6.1.2.1.10.166.11.1.3.1.1.2";
    }

    leaf mplsL3VpnVrfPerfCurrNumRoutes {
      type yang:gauge32;
      description
       "Indicates the number of routes currently used by this
        VRF.";
      smiv2:max-access "read-only";
      smiv2:oid "1.3.6.1.2.1.10.166.11.1.3.1.1.3";
    }

    leaf mplsL3VpnVrfPerfRoutesDropped {
      type yang:counter32;
      description
       "This counter should be incremented when the number of routes
        contained by the specified VRF exceeds or attempts to exceed
        the maximum allowed value as indicated by
        mplsL3VpnVrfMaxRouteThreshold.
        
        Discontinuities in the value of this counter can occur
        at re-initialization of the management system, and at
        other times as indicated by the value of
        mplsL3VpnVrfPerfDiscTime.";
      smiv2:max-access "read-only";
      smiv2:oid "1.3.6.1.2.1.10.166.11.1.3.1.1.4";
    }

    leaf mplsL3VpnVrfPerfDiscTime {
      type yang:timestamp;
      description
       "The value of sysUpTime on the most recent occasion at
        which any one or more of this entry's counters suffered
        a discontinuity.  If no such discontinuities have
        occurred since the last re-initialization of the local
        management subsystem, then this object contains a zero
        value.";
      smiv2:max-access "read-only";
      smiv2:oid "1.3.6.1.2.1.10.166.11.1.3.1.1.5";
    }
  }

  notification mplsL3VpnVrfUp {
    description
     "This notification is generated when:
      a. No interface is associated with this VRF, and the first
         (and only first) interface associated with it has its
         ifOperStatus change to up(1).
      
      b. One interface is associated with this VRF, and
         the ifOperStatus of this interface changes to up(1).
      
      c. Multiple interfaces are associated with this VRF, and the
         ifOperStatus of all interfaces is down(2), and the first
         of those interfaces has its ifOperStatus change to up(1).";
    smiv2:oid "1.3.6.1.2.1.10.166.11.0.1";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnIfConfIndex {
        type leafref {
          path "/MPLS-L3VPN-STD-MIB:MPLS-L3VPN-STD-MIB/MPLS-L3VPN-STD-MIB:mplsL3VpnIfConfTable/MPLS-L3VPN-STD-MIB:mplsL3VpnIfConfEntry/MPLS-L3VPN-STD-MIB:mplsL3VpnIfConfIndex";
        }
      }

      leaf mplsL3VpnIfConfRowStatus {
        type leafref {
          path "/MPLS-L3VPN-STD-MIB:MPLS-L3VPN-STD-MIB/MPLS-L3VPN-STD-MIB:mplsL3VpnIfConfTable/MPLS-L3VPN-STD-MIB:mplsL3VpnIfConfEntry/MPLS-L3VPN-STD-MIB:mplsL3VpnIfConfRowStatus";
        }
      }
    }

    container object-2 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfOperStatus {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfOperStatus";
        }
      }
    }
  }

  notification mplsL3VpnVrfDown {
    description
     "This notification is generated when:
      a. One interface is associated with this VRF, and
         the ifOperStatus of this interface changes from up(1)
         to down(2).
      
      b. Multiple interfaces are associated with this VRF, and
         the ifOperStatus of all except one of these interfaces is
         equal to up(1), and the ifOperStatus of that interface
         changes from up(1) to down(2).
      
      c. The last interface with ifOperStatus equal to up(1)
         is disassociated from a VRF.";
    smiv2:oid "1.3.6.1.2.1.10.166.11.0.2";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnIfConfIndex {
        type leafref {
          path "/MPLS-L3VPN-STD-MIB:MPLS-L3VPN-STD-MIB/MPLS-L3VPN-STD-MIB:mplsL3VpnIfConfTable/MPLS-L3VPN-STD-MIB:mplsL3VpnIfConfEntry/MPLS-L3VPN-STD-MIB:mplsL3VpnIfConfIndex";
        }
      }

      leaf mplsL3VpnIfConfRowStatus {
        type leafref {
          path "/MPLS-L3VPN-STD-MIB:MPLS-L3VPN-STD-MIB/MPLS-L3VPN-STD-MIB:mplsL3VpnIfConfTable/MPLS-L3VPN-STD-MIB:mplsL3VpnIfConfEntry/MPLS-L3VPN-STD-MIB:mplsL3VpnIfConfRowStatus";
        }
      }
    }

    container object-2 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfOperStatus {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfOperStatus";
        }
      }
    }
  }

  notification mplsL3VpnVrfRouteMidThreshExceeded {
    description
     "This notification is generated when the number of routes
      contained by the specified VRF exceeds the value indicated by
      mplsL3VpnVrfMidRouteThreshold.  A single notification MUST be
      generated when this threshold is exceeded, and no other
      notifications of this type should be issued until the value
      of mplsL3VpnVrfPerfCurrNumRoutes has fallen below that of
      mplsL3VpnVrfConfMidRteThresh.";
    smiv2:oid "1.3.6.1.2.1.10.166.11.0.3";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfPerfCurrNumRoutes {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfPerfCurrNumRoutes";
        }
      }
    }

    container object-2 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfConfMidRteThresh {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfConfMidRteThresh";
        }
      }
    }
  }

  notification mplsL3VpnVrfNumVrfRouteMaxThreshExceeded {
    description
     "This notification is generated when the number of routes
      contained by the specified VRF exceeds or attempts to exceed
      the maximum allowed value as indicated by
      mplsL3VpnVrfMaxRouteThreshold.  In cases where
      mplsL3VpnVrfConfHighRteThresh is set to the same value
      as mplsL3VpnVrfConfMaxRoutes, mplsL3VpnVrfConfHighRteThresh
      need not be exceeded; rather, just reached for this notification
      to be issued.
      
      Note that mplsL3VpnVrfConfRteMxThrshTime denotes the interval
      at which the this notification will be reissued after the
      maximum value has been exceeded (or reached if
      mplsL3VpnVrfConfMaxRoutes and mplsL3VpnVrfConfHighRteThresh are
      equal) and the initial notification has been issued.  This value
      is intended to prevent continuous generation of notifications by
      an agent in the event that routes are continually added to a VRF
      after it has reached its maximum value.  The default value is 0
      minutes.  If this value is set to 0, the agent should only issue
      a single notification at the time that the maximum threshold has
      been reached, and should not issue any more notifications until
      the value of routes has fallen below the configured threshold
      value.";
    smiv2:oid "1.3.6.1.2.1.10.166.11.0.4";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfPerfCurrNumRoutes {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfPerfCurrNumRoutes";
        }
      }
    }

    container object-2 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfConfHighRteThresh {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfConfHighRteThresh";
        }
      }
    }
  }

  notification mplsL3VpnNumVrfSecIllglLblThrshExcd {
    description
     "This notification is generated when the number of illegal
      label violations on a VRF as indicated by
      
      mplsL3VpnVrfSecIllegalLblVltns has exceeded
      mplsL3VpnIllLblRcvThrsh.  The threshold is not
      included in the varbind here because the value of
      mplsL3VpnVrfSecIllegalLblVltns should be one greater than
      the threshold at the time this notification is issued.";
    smiv2:oid "1.3.6.1.2.1.10.166.11.0.5";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfSecIllegalLblVltns {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfSecIllegalLblVltns";
        }
      }
    }
  }

  notification mplsL3VpnNumVrfRouteMaxThreshCleared {
    description
     "This notification is generated only after the number of routes
      contained by the specified VRF exceeds or attempts to exceed
      the maximum allowed value as indicated by
      mplsVrfMaxRouteThreshold, and then falls below this value.  The
      emission of this notification informs the operator that the
      error condition has been cleared without the operator having to
      query the device.
      
      Note that mplsL3VpnVrfConfRteMxThrshTime denotes the interval at
      which the mplsNumVrfRouteMaxThreshExceeded notification will
      be reissued after the maximum value has been exceeded (or
      reached if mplsL3VpnVrfConfMaxRoutes and
      mplsL3VpnVrfConfHighRteThresh are equal) and the initial
      notification has been issued.  Therefore,
      the generation of this notification should also be emitted with
      this same frequency (assuming that the error condition is
      cleared).  Specifically, if the error condition is reached and
      cleared several times during the period of time specified in
      mplsL3VpnVrfConfRteMxThrshTime, only a single notification will
      be issued to indicate the first instance of the error condition
      as well as the first time the error condition is cleared.
      This behavior is intended to prevent continuous generation of
      notifications by an agent in the event that routes are
      continually added and removed to/from a VRF after it has
      reached its maximum value.  The default value is 0.  If this
      value is set to 0, the agent should issue a notification
      whenever the maximum threshold has been cleared.";
    smiv2:oid "1.3.6.1.2.1.10.166.11.0.6";

    container object-1 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfPerfCurrNumRoutes {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfPerfCurrNumRoutes";
        }
      }
    }

    container object-2 {

      leaf mplsL3VpnVrfName {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfName";
        }
      }

      leaf mplsL3VpnVrfConfHighRteThresh {
        type leafref {
          path "/MPLS-L3VPN-STD-MIB:MPLS-L3VPN-STD-MIB/MPLS-L3VPN-STD-MIB:mplsL3VpnVrfTable/MPLS-L3VPN-STD-MIB:mplsL3VpnVrfEntry/MPLS-L3VPN-STD-MIB:mplsL3VpnVrfConfHighRteThresh";
        }
      }
    }
  }

  smiv2:alias "mplsL3VpnMIB" {
    smiv2:oid "1.3.6.1.2.1.10.166.11";
  }

  smiv2:alias "mplsL3VpnNotifications" {
    smiv2:oid "1.3.6.1.2.1.10.166.11.0";
  }

  smiv2:alias "mplsL3VpnObjects" {
    smiv2:oid "1.3.6.1.2.1.10.166.11.1";
  }

  smiv2:alias "mplsL3VpnScalars" {
    smiv2:oid "1.3.6.1.2.1.10.166.11.1.1";
  }

  smiv2:alias "mplsL3VpnConf" {
    smiv2:oid "1.3.6.1.2.1.10.166.11.1.2";
  }

  smiv2:alias "mplsL3VpnPerf" {
    smiv2:oid "1.3.6.1.2.1.10.166.11.1.3";
  }

  smiv2:alias "mplsL3VpnRoute" {
    smiv2:oid "1.3.6.1.2.1.10.166.11.1.4";
  }

  smiv2:alias "mplsL3VpnConformance" {
    smiv2:oid "1.3.6.1.2.1.10.166.11.2";
  }

  smiv2:alias "mplsL3VpnGroups" {
    smiv2:oid "1.3.6.1.2.1.10.166.11.2.1";
  }

  smiv2:alias "mplsL3VpnCompliances" {
    smiv2:oid "1.3.6.1.2.1.10.166.11.2.2";
  }

}
