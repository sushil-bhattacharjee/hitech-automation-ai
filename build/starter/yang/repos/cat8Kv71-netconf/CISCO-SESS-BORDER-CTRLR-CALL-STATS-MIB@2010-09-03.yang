/*
 * Generated by confdc --mib2yang-std
 * Source: mgmt/dmi/model/mib/src/CISCO-SESS-BORDER-CTRLR-CALL-STATS-MIB.mib
 */
/*
 * This YANG module has been generated by smidump 0.5.0:
 *
 *      smidump -f yang CISCO-SESS-BORDER-CTRLR-CALL-STATS-MIB
 *
 * Do not edit. Edit the source file instead!
 */

module CISCO-SESS-BORDER-CTRLR-CALL-STATS-MIB {

  namespace "urn:ietf:params:xml:ns:yang:smiv2:CISCO-SESS-BORDER-CTRLR-CALL-STATS-MIB";
  prefix CISCO-SESS-BORDER-CTRLR-CALL-STATS-MIB;

  import CISCO-TC {
    prefix "cisco-tc";
  }

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    Postal: 170 W Tasman Drive
    
    San Jose, CA  95134
    
    USA
    
    Tel: +1 800 553-NETS
    E-mail: sbc-dev@cisco.com";

  description
   "The main purpose of this MIB is to define the statistics
    information for Session Border Controller application. The 
    statistics are mainly of two types - Call statistics and 
    Media statistics. The calls can further be categorized as SIP 
    calls and H.248 calls.
    
    This MIB categorizes the statistics information into following
    four types:
    1. Global call statistics - Represents the global call related
       statistics like call rates, media flows, signaling flows
       etc.
    
    2. Periodic statistics - Represents the SBC call statistics 
       information for a particular time interval like current 5 
       minutes, previous 5 minutes, current 15 minutes, previous 15
       minutes, current hour and previous hour.
    
    3. Per flow statistics - Represents the SBC media flow 
       statistics. These are media statistics for each of the
       current ongoing call flow.
    
    4. H.248 statistics - Represents the H.248 call related 
       statistics information when H.248 controller is associated
       with SBC.
    
    The Session Border Controller (SBC) enables direct IP-to-IP
    interconnect between multiple administrative domains for
    session-based services providing protocol inter-working,
    security, and admission control and management. The SBC is a
    voice over IP (VoIP) device that sits on the border of a 
    network and controls call admission to that network. 
    
    The primary purpose of an SBC is to protect the interior of the
    network from excessive call load and malicious traffic.
    Additional functions provided by the SBC include media bridging
    and billing services. 
    
    
    GLOSSARY
    SBC: Session Border Controller
    
    CSB: CISCO Session Border Controller
    
    CAC: Call Admission Control - protects voice traffic from the
    negative effects of other voice traffic and to keep excess
    voice traffic off the network. It is used to prevent congestion
    in Voice traffic. It is used in the Call Setup phase.
    
    RTP: Real Time Transport Protocol - defines a standardized
    packet format for delivering audio and video over the Internet.
    
    RTCP: Real Time Control Protocol - It is a sister protocol of
    the Real-time Transport Protocol (RTP). RTCP provides
    out-of-band control information for an RTP flow. It partners
    RTP in the delivery and packaging of multimedia data, but does
    not transport any data itself. It is used periodically to
    transmit control packets to participants in a streaming
    multimedia session.
    
    VMG: Virtual Media Gateway - introduced to bridge between
    different transmission technologies and to add service to
    end-user connections. Its architecture separates control and
    connectivity functions into physically separate network layers.
    
    VPN: Virtual Private Network - It is a communications network
    tunneled through another network, and dedicated for a specific
    network.
    
    Gate Id - Context Identifiers assigned uniquely to a SIP/H.248
    call flows.
    
    Flow Pair Id: Stream Identifiers assigned uniquely to a
    SIP/H.248 call flows.
    
    Adjacency: An adjacency contains the system information to be
    transmitted to next HOP.
    
    REFERENCES
    1. CISCO Session Border Controller Documents and FAQ
    http://zed.cisco.com/confluence/display/SBC/SBC";

  revision 2010-09-03 {
    description
     "Updated existing tables by adding new fields. Below is the
      description of changes for each table-
      
      1. The statistics fields introduced in csbCallStatsTable are -
              csbCallStatsAvailableTranscodeFlows
              csbCallStatsActiveTranscodeFlows
              csbCallStatsPeakTranscodeFlows
              csbCallStatsTotalTranscodeFlows
      
      2. The statistics fields introduced in csbCurrPeriodicStatsTable
      are -
      
              csbCurrPeriodicStatsTranscodedCalls
              csbCurrPeriodicStatsTransratedCalls
              csbCurrPeriodicStatsTotalCallUpdateFailure
              csbCurrPeriodicStatsActiveIpv6Calls
              csbCurrPeriodicStatsActiveE2EmergencyCalls
              csbCurrPeriodicStatsImsRxActiveCalls
              csbCurrPeriodicStatsImsRxCallSetupFaiures
              csbCurrPeriodicStatsImsRxCallRenagotiationAttempts
              csbCurrPeriodicStatsImsRxCallRenagotiationFailures
              csbCurrPeriodicStatsAudioTranscodedCalls
              csbCurrPeriodicStatsFaxTranscodedCalls
              csbCurrPeriodicStatsRtpDisallowedFailures
              csbCurrPeriodicStatsSrtpDisallowedFailures
              csbCurrPeriodicStatsNonSrtpCalls
              csbCurrPeriodicStatsSrtpNonIwCalls
              csbCurrPeriodicStatsSrtpIwCalls
              csbCurrPeriodicStatsDtmfIw2833Calls
              csbCurrPeriodicStatsDtmfIwInbandCalls
              csbCurrPeriodicStatsDtmfIw2833InbandCalls
              csbCurrPeriodicStatsTotalTapsRequested
              csbCurrPeriodicStatsTotalTapsSucceeded
              csbCurrPeriodicStatsCurrentTaps
      
      3. The statistics fields introduced in csbHistoryStatsTable
      are-
      
              csbHistoryStatsTranscodedCalls
              csbHistoryStatsTransratedCalls
              csbHistoryStatsTotalCallUpdateFailure
              csbHistoryStatsActiveIpv6Calls
              csbHistoryStatsActiveE2EmergencyCalls
              csbHistoryStatsImsRxActiveCalls
              csbHistoryStatsImsRxCallSetupFaiures
              csbHistoryStatsImsRxCallRenagotiationAttempts
              csbHistoryStatsImsRxCallRenagotiationFailures
              csbHistoryStatsAudioTranscodedCalls
              csbHistoryStatsFaxTranscodedCalls
              csbHistoryStatsRtpDisallowedFailures
              csbHistoryStatsSrtpDisallowedFailures
              csbHistoryStatsNonSrtpCalls
              csbHistoryStatsSrtpNonIwCalls
              csbHistoryStatsSrtpIwCalls
              csbHistoryStatsDtmfIw2833Calls
              csbHistoryStatsDtmfIwInbandCalls
              csbHistoryStatsDtmfIw2833InbandCalls
              csbHistoryStatsTotalTapsRequested
              csbHistoryStatsTotalTapsSucceeded
              csbHistoryStatsCurrentTaps
      
      4. The statistics field introduced in csbPerFlowStatsTable is-
              csbPerFlowStatsRTPPktsLost";
  }

  revision 2008-08-27 {
    description
     "Updated description for following objects
      csbPerFlowStatsRTCPPktsSent 
      csbPerFlowStatsRTCPPktsRcvd
      csbPerFlowStatsRTCPPktsLost
      Deprecated the csbH248StatsTable and replaced it with 
      csbH248StatsRev1Table to correct problem with index.";
  }

  revision 2008-05-29 {
    description
     "Initial version of the MIB module.";
  }

  typedef CiscoSbcPeriodicStatsInterval {
    type enumeration {
      enum "fiveMinute" {
        value "1";
      }
      enum "fifteenMinute" {
        value "2";
      }
      enum "oneHour" {
        value "3";
      }
      enum "oneDay" {
        value "4";
      }
    }
    description
     "This textual convention represents the interval values for
      which the periodic stats and history stats are to be displayed.
      fiveMinute - Interval to display current/previous 5 minutes
      statistics information.
      fifteenMinute - Interval to display current/previous 15 minutes
      statistics information.
      oneHour - Interval to display current/previous one hour
      statistics information.
      oneDay - Interval to display current/previous one day
      statistics information.";
  }


  container CISCO-SESS-BORDER-CTRLR-CALL-STATS-MIB {
    config false;

    container csbCallStatsInstanceTable {
      description
       "The call stats instance table contains the physical index for
        each of the physical entity (line card, primary, secondary
        cards). The index of the table is instance index which uniquely
        identifies the physical entity present on the box.";
      smiv2:oid "1.3.6.1.4.1.9.9.657.1.1";

      list csbCallStatsInstanceEntry {
        key "csbCallStatsInstanceIndex";
        description
         "A conceptual row in csbCallStatsInstanceTable. There is an
          entry in this table for each SBC instance, as identified by a 
          value of csbCallStatsInstanceIndex.";
        smiv2:oid "1.3.6.1.4.1.9.9.657.1.1.1";

        leaf csbCallStatsInstanceIndex {
          type uint32;
          description
           "This object uniquely identifies the sequence number of an
            entity or slot that is configured per device. This index is
            assigned arbitrarily by the engine and is not saved over
            reboots.";
          smiv2:max-access "not-accessible";
          smiv2:oid "1.3.6.1.4.1.9.9.657.1.1.1.1";
        }

        leaf csbCallStatsInstancePhysicalIndex {
          type cisco-tc:EntPhysicalIndexOrZero;
          description
           "This object indicates the physical entity for which all the
            measurements are maintained. The exact type of this
            entity is described by its entPhysicalVendorType value.";
          smiv2:max-access "read-only";
          smiv2:oid "1.3.6.1.4.1.9.9.657.1.1.1.2";
        }
      }
    }

    container csbCallStatsTable {
      description
       "This table describes the global statistics information in the
        form of a table which contains call specific information like
        call rates, media flows, signaling flows etc. The index of the
        table is service index which corresponds to a particular 
        service configured on the SBC and all the rows of the table
        represents the global information regarding all the call flows
        related to that particular service. The other index of this
        table is csbCallStatsInstanceIndex which is defined in
        csbCallStatsInstanceTable.";
      smiv2:oid "1.3.6.1.4.1.9.9.657.1.2";

      list csbCallStatsEntry {
        key "csbCallStatsInstanceIndex csbCallStatsServiceIndex";
        description
         "An conceptual row in the csbCallStatsGlobalStatsTable. There is
          an entry in this table for the particular service configured on
          SBC identified by a value of csbCallStatsInstanceIndex. The
          other index of this table is csbCallStatsInstanceIndex which is
          defined in csbCallStatsInstanceTable.";
        smiv2:oid "1.3.6.1.4.1.9.9.657.1.2.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type uint32;
          description
           "This object identifies the index of the name of the SBC
            service configured. This object also acts as an index for the
            table.";
          smiv2:max-access "not-accessible";
          smiv2:oid "1.3.6.1.4.1.9.9.657.1.2.1.1";
        }

        leaf csbCallStatsSbcName {
          type snmp-framework:SnmpAdminString;
          description
           "This object indicates the configured name of the SBC service.
            The length of this object is zero when value is not assigned
            to it.";
          smiv2:max-access "read-only";
          smiv2:oid "1.3.6.1.4.1.9.9.657.1.2.1.2";
        }

        leaf csbCallStatsCallsHigh {
          type uint32;
          units "calls per second";
          description
           "This object indicates the maximum number of calls per second
            processed by the Session Border Controller in past 24 hours.";
          smiv2:max-access "read-only";
          smiv2:oid "1.3.6.1.4.1.9.9.657.1.2.1.3";
        }

        leaf csbCallStatsRate1Sec {
          type yang:gauge32;
          units "calls per second";
          description
           "This object indicates the average calls per second processed by
            the Session Border Controller.";
          smiv2:max-access "read-only";
          smiv2:oid "1.3.6.1.4.1.9.9.657.1.2.1.4";
        }

        leaf csbCallStatsCallsLow {
          type uint32;
          units "calls per second";
          description
           "This object indicates the minimum calls per second in past 24
            hours.";
          smiv2:max-access "read-only";
          smiv2:oid "1.3.6.1.4.1.9.9.657.1.2.1.5";
        }

        leaf csbCallStatsAvailableFlows {
          type yang:gauge32;
          units "flows";
          description
           "This object indicates the number of media flows which are
            available.";
          smiv2:max-access "read-only";
          smiv2:oid "1.3.6.1.4.1.9.9.657.1.2.1.6";
        }

        leaf csbCallStatsUsedFlows {
          type yang:gauge32;
          units "flows";
          description
           "This object indicates the number of media flows which are
            used. This is for the flow allocated and connected. The flow
            allocated but not connected is not counted.";
          smiv2:max-access "read-only";
          smiv2:oid "1.3.6.1.4.1.9.9.657.1.2.1.7";
        }

        leaf csbCallStatsPeakFlows {
          type uint32;
          units "flows";
          description
           "This object indicates the number of peak flows in SBC.
            This is the highest recorded value for the active flows since
            the box was booted/reseted.";
          smiv2:max-access "read-only";
          smiv2:oid "1.3.6.1.4.1.9.9.657.1.2.1.8";
        }

        leaf csbCallStatsTotalFlows {
          type uint32;
          units "flows";
          description
           "This object indicates the total number of media support by this
            instance of SBC. The total number of flows include the
            available
            flows and the active flows. This value is since box was
            booted/reseted. Total flows include the active flows and the
            flows allocated but not connected.";
          smiv2:max-access "read-only";
          smiv2:oid "1.3.6.1.4.1.9.9.657.1.2.1.9";
        }

        leaf csbCallStatsUsedSigFlows {
          type yang:gauge32;
          units "signal flows";
          description
           "This object indicates the number of active signaling flows for
            signaling pinholes.";
          smiv2:max-access "read-only";
          smiv2:oid "1.3.6.1.4.1.9.9.657.1.2.1.10";
        }

        leaf csbCallStatsPeakSigFlows {
          type uint32;
          units "signal flows";
          description
           "This object indicates the peak signaling flow in SBC.
            This is the highest recorded value for the active signaling
            flows. This object is calculated using csbCallStatsUsedFlows.";
          smiv2:max-access "read-only";
          smiv2:oid "1.3.6.1.4.1.9.9.657.1.2.1.11";
        }

        leaf csbCallStatsTotalSigFlows {
          type uint32;
          units "signal flows";
          description
           "This object indicates the maximum number of Signalling Flows
            that can be supported by this instance of SBC.";
          smiv2:max-access "read-only";
          smiv2:oid "1.3.6.1.4.1.9.9.657.1.2.1.12";
        }

        leaf csbCallStatsAvailablePktRate {
          type yang:gauge32;
          units "packets per second";
          description
           "This object indicates the remaining capacity that can be
            supported by SBC.";
          smiv2:max-access "read-only";
          smiv2:oid "1.3.6.1.4.1.9.9.657.1.2.1.13";
        }

        leaf csbCallStatsUnclassifiedPkts {
          type yang:counter64;
          units "packets";
          description
           "This object indicates the number of unclassified packets
            processed by SBC.";
          smiv2:max-access "read-only";
          smiv2:oid "1.3.6.1.4.1.9.9.657.1.2.1.14";
        }

        leaf csbCallStatsRTPPktsSent {
          type yang:counter64;
          units "packets";
          description
           "This object indicates the total number of RTP packets sent.";
          smiv2:max-access "read-only";
          smiv2:oid "1.3.6.1.4.1.9.9.657.1.2.1.15";
        }

        leaf csbCallStatsRTPPktsRcvd {
          type yang:counter64;
          units "packets";
          description
           "This object indicates the total number of RTP packets
            received.";
          smiv2:max-access "read-only";
          smiv2:oid "1.3.6.1.4.1.9.9.657.1.2.1.16";
        }

        leaf csbCallStatsRTPPktsDiscard {
          type yang:counter64;
          units "packets";
          description
           "This object indicates the total number of RTP packets
            discarded.";
          smiv2:max-access "read-only";
          smiv2:oid "1.3.6.1.4.1.9.9.657.1.2.1.17";
        }

        leaf csbCallStatsRTPOctetsSent {
          type yang:counter64;
          units "octets";
          description
           "This object indicates the number of RTP octets sent by the
            SBC.";
          smiv2:max-access "read-only";
          smiv2:oid "1.3.6.1.4.1.9.9.657.1.2.1.18";
        }

        leaf csbCallStatsRTPOctetsRcvd {
          type yang:counter64;
          units "octets";
          description
           "This object indicates the number of RTP octets received by
            the SBC.";
          smiv2:max-access "read-only";
          smiv2:oid "1.3.6.1.4.1.9.9.657.1.2.1.19";
        }

        leaf csbCallStatsRTPOctetsDiscard {
          type yang:counter64;
          units "octets";
          description
           "This object indicates the number of RTP octets discarded by
            the SBC.";
          smiv2:max-access "read-only";
          smiv2:oid "1.3.6.1.4.1.9.9.657.1.2.1.20";
        }

        leaf csbCallStatsNoMediaCount {
          type yang:counter32;
          units "no media events";
          description
           "This object indicates the accumulated No media event
            count.";
          smiv2:max-access "read-only";
          smiv2:oid "1.3.6.1.4.1.9.9.657.1.2.1.21";
        }

        leaf csbCallStatsRouteErrors {
          type yang:counter32;
          units "route error events";
          description
           "This object indicates the accumulated route error event
            count. This counter is for the route error of media stream.";
          smiv2:max-access "read-only";
          smiv2:oid "1.3.6.1.4.1.9.9.657.1.2.1.22";
        }

        leaf csbCallStatsAvailableTranscodeFlows {
          type yang:gauge32;
          units "flows";
          description
           "This object indicates the number of additional transcoded flows
            that this media gateway manager (MGM) entity is currently able
            to configure.";
          smiv2:max-access "read-only";
          smiv2:oid "1.3.6.1.4.1.9.9.657.1.2.1.23";
        }

        leaf csbCallStatsActiveTranscodeFlows {
          type yang:gauge32;
          units "flows";
          description
           "This object indicates the current number of transcoded
            flows that are actively forwarding media traffic.  In this
            context, a flow is a media stream passing through the device.
            So a single voice call will be counted only once.";
          smiv2:max-access "read-only";
          smiv2:oid "1.3.6.1.4.1.9.9.657.1.2.1.24";
        }

        leaf csbCallStatsPeakTranscodeFlows {
          type uint32;
          units "flows";
          description
           "This object indicates the peak number of active transcoded
            flows since the statistics were last reset.  In this context, a
            flow is a media stream passing through the device, so a single
            voice call will be counted once.";
          smiv2:max-access "read-only";
          smiv2:oid "1.3.6.1.4.1.9.9.657.1.2.1.25";
        }

        leaf csbCallStatsTotalTranscodeFlows {
          type uint32;
          units "flows";
          description
           "This object indicates the accumulated total number of
            transcoded flows.  This count contains both active flows and
            flows that were allocated but never connected.  In this context,
            a flow is a media stream passing through the device, so a single
            voice call will be counted once.";
          smiv2:max-access "read-only";
          smiv2:oid "1.3.6.1.4.1.9.9.657.1.2.1.26";
        }
      }
    }

    container csbCurrPeriodicStatsTable {
      description
       "This table is used to collect measurement over several
        different intervals as defined by the
        csbCurrPeriodicStatsInterval object. When a new interval starts
        the objects associated with the interval are reset and count up
        throughout the interval. The index of the table is the interval
        for which the stats information is to be displayed. The interval
        values can be 5 min, 15 mins, 1 hour and one day. The other
        indices of this table are csbCallStatsInstanceIndex
        defined in csbCallStatsInstanceTable and
        csbCallStatsServiceIndex defined in csbCallStatsTable.
        
        The gauge values are reported as :-
        1.If the period being queried is current5mins, this is the value
        at the instant that the query is issued. 
        2.Otherwise, for the other intevals, this is an average value
        during the summary period sampled at 5 minute intervals.";
      smiv2:oid "1.3.6.1.4.1.9.9.657.1.3";

      list csbCurrPeriodicStatsEntry {
        key "csbCallStatsInstanceIndex csbCallStatsServiceIndex csbCurrPeriodicStatsInterval";
        description
         "An conceptual row in the csbCurrPeriodicStatsTable. There is
          an entry in this table for the particular controller by a value
          of csbH248StatsCtrlrIndex. The other indices of this table are
          csbCallStatsInstanceIndex defined in csbCallStatsInstanceTable
          and csbCallStatsServiceIndex defined in csbCallStatsTable.";
        smiv2:oid "1.3.6.1.4.1.9.9.657.1.3.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type leafref {
            path "/CISCO-SESS-BORDER-CTRLR-CALL-STATS-MIB:CISCO-SESS-BORDER-CTRLR-CALL-STATS-MIB/CISCO-SESS-BORDER-CTRLR-CALL-STATS-MIB:csbCallStatsTable/CISCO-SESS-BORDER-CTRLR-CALL-STATS-MIB:csbCallStatsEntry/CISCO-SESS-BORDER-CTRLR-CALL-STATS-MIB:csbCallStatsServiceIndex";
          }
        }

        leaf csbCurrPeriodicStatsInterval {
          type CISCO-SESS-BORDER-CTRLR-CALL-STATS-MIB:CiscoSbcPeriodicStatsInterval;
          description
           "This object identifies the interval for which the periodic
            statistics information is to be displayed. The interval
            values can be 5 min, 15 mins, 1 hour , 1 Day. This object acts
            as index for the table.";
          smiv2:max-access "not-accessible";
          smiv2:oid "1.3.6.1.4.1.9.9.657.1.3.1.1";
        }

        leaf csbCurrPeriodicStatsActiveCalls {
          type yang:gauge32;
          units "calls";
          description
           "This object indicates the number of calls that have become
            active during this interval.";
          smiv2:max-access "read-only";
          smiv2:oid "1.3.6.1.4.1.9.9.657.1.3.1.2";
        }

        leaf csbCurrPeriodicStatsActivatingCalls {
          type yang:gauge32;
          units "calls";
          description
           "This object indicates the number of calls that have become
            activing during this interval.";
          smiv2:max-access "read-only";
          smiv2:oid "1.3.6.1.4.1.9.9.657.1.3.1.3";
        }

        leaf csbCurrPeriodicStatsDeactivatingCalls {
          type yang:gauge32;
          units "calls";
          description
           "This object indicates the number of calls that have become
            deactiving during this interval.";
          smiv2:max-access "read-only";
          smiv2:oid "1.3.6.1.4.1.9.9.657.1.3.1.4";
        }

        leaf csbCurrPeriodicStatsTotalCallAttempts {
          type yang:gauge32;
          description
           "This object indicates the number of total call attempts during
            this interval.";
          smiv2:max-access "read-only";
          smiv2:oid "1.3.6.1.4.1.9.9.657.1.3.1.5";
        }

        leaf csbCurrPeriodicStatsFailedCallAttempts {
          type yang:gauge32;
          description
           "This object indicates the number of failed call attempts during
            this interval.";
          smiv2:max-access "read-only";
          smiv2:oid "1.3.6.1.4.1.9.9.657.1.3.1.6";
        }

        leaf csbCurrPeriodicStatsCallRoutingFailure {
          type yang:gauge32;
          description
           "This object indicates the number of call setup failures due
            to routing failures during this interval.";
          smiv2:max-access "read-only";
          smiv2:oid "1.3.6.1.4.1.9.9.657.1.3.1.7";
        }

        leaf csbCurrPeriodicStatsCallResourceFailure {
          type yang:gauge32;
          description
           "This object indicates the number of call setup failures due
            to resource failures during this interval.";
          smiv2:max-access "read-only";
          smiv2:oid "1.3.6.1.4.1.9.9.657.1.3.1.8";
        }

        leaf csbCurrPeriodicStatsCallMediaFailure {
          type yang:gauge32;
          description
           "This object indicates the number of call setup failures due
            to media failure during this interval.";
          smiv2:max-access "read-only";
          smiv2:oid "1.3.6.1.4.1.9.9.657.1.3.1.9";
        }

        leaf csbCurrPeriodicStatsCallSigFailure {
          type yang:gauge32;
          description
           "This object indicates the number of call setup failures due
            to signaling failure during this interval.";
          smiv2:max-access "read-only";
          smiv2:oid "1.3.6.1.4.1.9.9.657.1.3.1.10";
        }

        leaf csbCurrPeriodicStatsActiveCallFailure {
          type yang:gauge32;
          description
           "This object indicates the number of active call failures during
            this interval.";
          smiv2:max-access "read-only";
          smiv2:oid "1.3.6.1.4.1.9.9.657.1.3.1.11";
        }

        leaf csbCurrPeriodicStatsCongestionFailure {
          type yang:gauge32;
          description
           "This object indicates the number of call setup failures due
            to congestion during this interval.";
          smiv2:max-access "read-only";
          smiv2:oid "1.3.6.1.4.1.9.9.657.1.3.1.12";
        }

        leaf csbCurrPeriodicStatsCallSetupPolicyFailure {
          type yang:gauge32;
          description
           "This object indicates the number of call setup failures due
            to policy failure during this interval.";
          smiv2:max-access "read-only";
          smiv2:oid "1.3.6.1.4.1.9.9.657.1.3.1.13";
        }

        leaf csbCurrPeriodicStatsCallSetupNAPolicyFailure {
          type yang:gauge32;
          description
           "This object indicates the number of call setup failures due
            to NA policy failure during this interval.";
          smiv2:max-access "read-only";
          smiv2:oid "1.3.6.1.4.1.9.9.657.1.3.1.14";
        }

        leaf csbCurrPeriodicStatsCallSetupRoutingPolicyFailure {
          type yang:gauge32;
          description
           "This object indicates the number of call setup failures due
            to routing policy failure during this interval.";
          smiv2:max-access "read-only";
          smiv2:oid "1.3.6.1.4.1.9.9.657.1.3.1.15";
        }

        leaf csbCurrPeriodicStatsCallSetupCACPolicyFailure {
          type yang:gauge32;
          description
           "This object indicates the number of call setup failures due
            to CAC policy failure during this interval.";
          smiv2:max-access "read-only";
          smiv2:oid "1.3.6.1.4.1.9.9.657.1.3.1.16";
        }

        leaf csbCurrPeriodicStatsCallSetupCACCallLimitFailure {
          type yang:gauge32;
          description
           "This object indicates the number of call setup failures due
            to CAC call limit during this interval.";
          smiv2:max-access "read-only";
          smiv2:oid "1.3.6.1.4.1.9.9.657.1.3.1.17";
        }

        leaf csbCurrPeriodicStatsCallSetupCACRateLimitFailure {
          type yang:gauge32;
          description
           "This object indicates the number of call setup failures due
            to CAC call rate limit during this interval.";
          smiv2:max-access "read-only";
          smiv2:oid "1.3.6.1.4.1.9.9.657.1.3.1.18";
        }

        leaf csbCurrPeriodicStatsCallSetupCACBandwidthFailure {
          type yang:gauge32;
          description
           "This object indicates the number of call setup failures due
            to CAC bandwidth limit during this interval.";
          smiv2:max-access "read-only";
          smiv2:oid "1.3.6.1.4.1.9.9.657.1.3.1.19";
        }

        leaf csbCurrPeriodicStatsCallSetupCACMediaLimitFailure {
          type yang:gauge32;
          description
           "This object indicates the number of call setup failures due
            to CAC media limit during this interval.";
          smiv2:max-access "read-only";
          smiv2:oid "1.3.6.1.4.1.9.9.657.1.3.1.20";
        }

        leaf csbCurrPeriodicStatsCallSetupCACMediaUpdateFailure {
          type yang:gauge32;
          description
           "This object indicates the number of call update failure due
            to policy failure during this interval.";
          smiv2:max-access "read-only";
          smiv2:oid "1.3.6.1.4.1.9.9.657.1.3.1.21";
        }

        leaf csbCurrPeriodicStatsTimestamp {
          type binary {
            length "0..80";
          }
          description
           "This object indicates the current time at the start of each
            interval.";
          smiv2:max-access "read-only";
          smiv2:oid "1.3.6.1.4.1.9.9.657.1.3.1.22";
        }

        leaf csbCurrPeriodicStatsTranscodedCalls {
          type yang:gauge32;
          units "calls";
          description
           "The object indicates the number of transcoded calls that are
            active during this interval.";
          smiv2:max-access "read-only";
          smiv2:oid "1.3.6.1.4.1.9.9.657.1.3.1.23";
        }

        leaf csbCurrPeriodicStatsTransratedCalls {
          type yang:gauge32;
          units "calls";
          description
           "The object indicates the number of transrated calls that are
            active during this interval.";
          smiv2:max-access "read-only";
          smiv2:oid "1.3.6.1.4.1.9.9.657.1.3.1.24";
        }

        leaf csbCurrPeriodicStatsTotalCallUpdateFailure {
          type yang:gauge32;
          units "calls";
          description
           "This object indicates the total number of call update failures
            during this interval.";
          smiv2:max-access "read-only";
          smiv2:oid "1.3.6.1.4.1.9.9.657.1.3.1.25";
        }

        leaf csbCurrPeriodicStatsActiveIpv6Calls {
          type yang:gauge32;
          units "calls";
          description
           "This Object indicates the number of calls through SBC that use
            IPv6 signaling.  This statistic totals all calls that traverse
            an IPv6 adjacency on either or both sides of SBC during this
            interval.";
          smiv2:max-access "read-only";
          smiv2:oid "1.3.6.1.4.1.9.9.657.1.3.1.26";
        }

        leaf csbCurrPeriodicStatsActiveEmergencyCalls {
          type yang:gauge32;
          units "calls";
          description
           "This object indicates the number of calls through SBC that have
            been identified as emergency calls (by Number Analysis) during
            this interval.";
          smiv2:max-access "read-only";
          smiv2:oid "1.3.6.1.4.1.9.9.657.1.3.1.27";
        }

        leaf csbCurrPeriodicStatsActiveE2EmergencyCalls {
          type yang:gauge32;
          units "calls";
          description
           "This object indicates the number of calls through SBC that have
            been identified as emergency calls (by Number Analysis) and
            have used the e2 interface to obtain location information for
            the caller during this interval.";
          smiv2:max-access "read-only";
          smiv2:oid "1.3.6.1.4.1.9.9.657.1.3.1.28";
        }

        leaf csbCurrPeriodicStatsImsRxActiveCalls {
          type yang:gauge32;
          units "calls";
          description
           "This object indicates the total number of active calls which
            use IMS Rx, during this interval.";
          smiv2:max-access "read-only";
          smiv2:oid "1.3.6.1.4.1.9.9.657.1.3.1.29";
        }

        leaf csbCurrPeriodicStatsImsRxCallSetupFaiures {
          type yang:gauge32;
          units "failures";
          description
           "This object indicates the total call Setup failures owing to
            IMS Rx failure during this interval.";
          smiv2:max-access "read-only";
          smiv2:oid "1.3.6.1.4.1.9.9.657.1.3.1.30";
        }

        leaf csbCurrPeriodicStatsImsRxCallRenegotiationAttempts {
          type yang:gauge32;
          units "attempts";
          description
           "This object indicates the total call renegotiation attempts
            using IMS Rx during this interval.";
          smiv2:max-access "read-only";
          smiv2:oid "1.3.6.1.4.1.9.9.657.1.3.1.31";
        }

        leaf csbCurrPeriodicStatsImsRxCallRenegotiationFailures {
          type yang:gauge32;
          units "failures";
          description
           "This object indicates the total call renegotiation failures
            owing to IMS Rx failure during this interval.";
          smiv2:max-access "read-only";
          smiv2:oid "1.3.6.1.4.1.9.9.657.1.3.1.32";
        }

        leaf csbCurrPeriodicStatsAudioTranscodedCalls {
          type yang:gauge32;
          units "calls";
          description
           "The number of active audio transcoded calls through
            this adjacency or account during this interval.";
          smiv2:max-access "read-only";
          smiv2:oid "1.3.6.1.4.1.9.9.657.1.3.1.33";
        }

        leaf csbCurrPeriodicStatsFaxTranscodedCalls {
          type yang:gauge32;
          units "calls";
          description
           "This object indicates the the number of active fax
            transcoded calls through this adjacency or account during this
            interval.";
          smiv2:max-access "read-only";
          smiv2:oid "1.3.6.1.4.1.9.9.657.1.3.1.34";
        }

        leaf csbCurrPeriodicStatsRtpDisallowedFailures {
          type yang:gauge32;
          units "failures";
          description
           "This object indicates the total call setup failures due to RTP
            being proposed when not permitted during this interval.";
          smiv2:max-access "read-only";
          smiv2:oid "1.3.6.1.4.1.9.9.657.1.3.1.35";
        }

        leaf csbCurrPeriodicStatsSrtpDisallowedFailures {
          type yang:gauge32;
          units "failures";
          description
           "This object indicates the total call setup failures due to SRTP
            being proposed when not permitted during this interval.";
          smiv2:max-access "read-only";
          smiv2:oid "1.3.6.1.4.1.9.9.657.1.3.1.36";
        }

        leaf csbCurrPeriodicStatsNonSrtpCalls {
          type yang:gauge32;
          units "calls";
          description
           "This object indicates the number of active calls
            through this adjacency or account which do not use SRTP on any
            media channels during this interval.";
          smiv2:max-access "read-only";
          smiv2:oid "1.3.6.1.4.1.9.9.657.1.3.1.37";
        }

        leaf csbCurrPeriodicStatsSrtpNonIwCalls {
          type yang:gauge32;
          units "calls";
          description
           "This object indicates the number of active calls
            through this adjacency or account that have one or more media
            channels which use SRTP. This count does not include media 
            channels that provide interworking between RTP and SRTP during
            this interval.";
          smiv2:max-access "read-only";
          smiv2:oid "1.3.6.1.4.1.9.9.657.1.3.1.38";
        }

        leaf csbCurrPeriodicStatsSrtpIwCalls {
          type yang:gauge32;
          units "calls";
          description
           "This object indicates the number of active calls
            through this adjacency or account that have one or more media
            channels that provide interworking between RTP and SRTP during
            this interval.";
          smiv2:max-access "read-only";
          smiv2:oid "1.3.6.1.4.1.9.9.657.1.3.1.39";
        }

        leaf csbCurrPeriodicStatsDtmfIw2833Calls {
          type yang:gauge32;
          units "calls";
          description
           "This object indicates the number of active calls
            through this adjacency or account for which DTMF interworking
            is enabled between DTMF in signaling and DTMF in media via RFC
            2833 during this interval.";
          smiv2:max-access "read-only";
          smiv2:oid "1.3.6.1.4.1.9.9.657.1.3.1.40";
        }

        leaf csbCurrPeriodicStatsDtmfIwInbandCalls {
          type yang:gauge32;
          units "calls";
          description
           "This object indicates the number of active calls
            through this adjacency or account for which DTMF interworking
            is enabled between DTMF in signaling and DTMF in media via 
            inband DTMF tones during this interval.";
          smiv2:max-access "read-only";
          smiv2:oid "1.3.6.1.4.1.9.9.657.1.3.1.41";
        }

        leaf csbCurrPeriodicStatsDtmfIw2833InbandCalls {
          type yang:gauge32;
          units "calls";
          description
           "This object indicates the number of active calls
            through this adjacency or account for which DTMF interworking
            is enabled between DTMF in media via RFC 2833 and DTMF in media
            via inband DTMF tones during this interval.";
          smiv2:max-access "read-only";
          smiv2:oid "1.3.6.1.4.1.9.9.657.1.3.1.42";
        }

        leaf csbCurrPeriodicStatsTotalTapsRequested {
          type yang:gauge32;
          units "attempts";
          description
           "This object indicates the lawful intercept tap attempts
            requested within the scope of this query during this interval.";
          smiv2:max-access "read-only";
          smiv2:oid "1.3.6.1.4.1.9.9.657.1.3.1.43";
        }

        leaf csbCurrPeriodicStatsTotalTapsSucceeded {
          type yang:gauge32;
          units "success";
          description
           "This object indicates the lawful intercept tap attempts that
            have been successfully implemented within the scope of this
            query during this interval.";
          smiv2:max-access "read-only";
          smiv2:oid "1.3.6.1.4.1.9.9.657.1.3.1.44";
        }

        leaf csbCurrPeriodicStatsCurrentTaps {
          type yang:gauge32;
          units "taps";
          description
           "This object indicates the Lawful intercept taps currently in
            place on calls within the scope of this query during this
            interval.";
          smiv2:max-access "read-only";
          smiv2:oid "1.3.6.1.4.1.9.9.657.1.3.1.45";
        }

        leaf csbCurrPeriodicIpsecCalls {
          type yang:gauge32;
          units "calls";
          description
           "The number of active calls on this adjacency or account which
            are to or from registered subscribers using IPSEC during this
            interval.";
          smiv2:max-access "read-only";
          smiv2:oid "1.3.6.1.4.1.9.9.657.1.3.1.46";
        }
      }
    }

    container csbHistoryStatsTable {
      description
       "This table provide historical measurement in various interval
        length defined by the csbHistoryStatsInterval object. Each
        interval may contain one or more entries to allow for detailed
        measurment to be collected. It is up to the platform to
        determine the number of intervals to be supported like 
        5 minutes, 15 minutes, 1 hour and 1 day. In addition, the number
        of
        historical entries is also determined by the platform
        resources.
        
        The gauge values are reported as:
        If the period being queried is previous5mins, this is the number
        of calls that were active at the end of the previous 5 minute
        period. Otherwise for the other intevals, this is an average
        value during the summary period, sampled at 5 minute intervals.";
      smiv2:oid "1.3.6.1.4.1.9.9.657.1.4";

      list csbHistoryStatsEntry {
        key "csbCallStatsInstanceIndex csbCallStatsServiceIndex csbHistoryStatsInterval csbHistoryStatsElements";
        description
         "A conceptual row in the csbHistoryStatsTable. The entries in
          this table are updated as interval completes in the
          csbCurrPeriodicStatsTable table and the data is moved from that
          table to this one.";
        smiv2:oid "1.3.6.1.4.1.9.9.657.1.4.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type leafref {
            path "/CISCO-SESS-BORDER-CTRLR-CALL-STATS-MIB:CISCO-SESS-BORDER-CTRLR-CALL-STATS-MIB/CISCO-SESS-BORDER-CTRLR-CALL-STATS-MIB:csbCallStatsTable/CISCO-SESS-BORDER-CTRLR-CALL-STATS-MIB:csbCallStatsEntry/CISCO-SESS-BORDER-CTRLR-CALL-STATS-MIB:csbCallStatsServiceIndex";
          }
        }

        leaf csbHistoryStatsInterval {
          type CISCO-SESS-BORDER-CTRLR-CALL-STATS-MIB:CiscoSbcPeriodicStatsInterval;
          description
           "This object identifies the interval for which the history
            statistics information is to be displayed. The interval
            values can be 5 min, 15 mins, 1 hour , 1 day. This object acts
            as index for the table.";
          smiv2:max-access "not-accessible";
          smiv2:oid "1.3.6.1.4.1.9.9.657.1.4.1.1";
        }

        leaf csbHistoryStatsElements {
          type uint32;
          description
           "The platform assigns a number starting with one and
            increments it each for each new row. When the maximum         
            number of row is reached the oldest rows are deleted. It is up
            to the platform to determine the number of entries for each
            interval. It is recommended that each platform support at least
            one entry for 5 min, 15 mins, 1 hour and 1 day intervals.";
          smiv2:max-access "not-accessible";
          smiv2:oid "1.3.6.1.4.1.9.9.657.1.4.1.2";
        }

        leaf csbHistoryStatsActiveCalls {
          type yang:gauge32;
          units "calls";
          description
           "This object indicates the number of active calls history during
            this interval.";
          smiv2:max-access "read-only";
          smiv2:oid "1.3.6.1.4.1.9.9.657.1.4.1.3";
        }

        leaf csbHistoryStatsTotalCallAttempts {
          type yang:gauge32;
          description
           "This object indicates the number of total call attempts history
            during this interval.";
          smiv2:max-access "read-only";
          smiv2:oid "1.3.6.1.4.1.9.9.657.1.4.1.4";
        }

        leaf csbHistoryStatsFailedCallAttempts {
          type yang:gauge32;
          description
           "This object indicates the number of failed call attempts during
            this interval.";
          smiv2:max-access "read-only";
          smiv2:oid "1.3.6.1.4.1.9.9.657.1.4.1.5";
        }

        leaf csbHistoryStatsCallRoutingFailure {
          type yang:gauge32;
          description
           "This object indicates the number of call setup failures due
            to routing failures during this interval.";
          smiv2:max-access "read-only";
          smiv2:oid "1.3.6.1.4.1.9.9.657.1.4.1.6";
        }

        leaf csbHistoryStatsCallResourceFailure {
          type yang:gauge32;
          description
           "This object indicates the number of call setup failures due
            to resource failures during this interval.";
          smiv2:max-access "read-only";
          smiv2:oid "1.3.6.1.4.1.9.9.657.1.4.1.7";
        }

        leaf csbHistoryStatsCallMediaFailure {
          type yang:gauge32;
          description
           "This object indicates the number of call setup failures due
            to media failure during this interval.";
          smiv2:max-access "read-only";
          smiv2:oid "1.3.6.1.4.1.9.9.657.1.4.1.8";
        }

        leaf csbHistoryStatsFailSigFailure {
          type yang:gauge32;
          description
           "This object indicates the number of call setup failures due
            to signaling failure during this interval.";
          smiv2:max-access "read-only";
          smiv2:oid "1.3.6.1.4.1.9.9.657.1.4.1.9";
        }

        leaf csbHistoryStatsActiveCallFailure {
          type yang:gauge32;
          description
           "This object indicates the number of active call failures during
            this interval.";
          smiv2:max-access "read-only";
          smiv2:oid "1.3.6.1.4.1.9.9.657.1.4.1.10";
        }

        leaf csbHistoryStatsCongestionFailure {
          type yang:gauge32;
          description
           "This object indicates the number of call setup failures due
            to congestion during this interval.";
          smiv2:max-access "read-only";
          smiv2:oid "1.3.6.1.4.1.9.9.657.1.4.1.11";
        }

        leaf csbHistoryStatsCallSetupPolicyFailure {
          type yang:gauge32;
          description
           "This object indicates the number of call setup failures due
            to some policy violations during this interval.";
          smiv2:max-access "read-only";
          smiv2:oid "1.3.6.1.4.1.9.9.657.1.4.1.12";
        }

        leaf csbHistoryStatsCallSetupNAPolicyFailure {
          type yang:gauge32;
          description
           "This object indicates the number of call setup failures due
            to NA policy failure during this interval.";
          smiv2:max-access "read-only";
          smiv2:oid "1.3.6.1.4.1.9.9.657.1.4.1.13";
        }

        leaf csbHistoryStatsCallSetupRoutingPolicyFailure {
          type yang:gauge32;
          description
           "This object indicates the number of call setup failures due
            to routing policy failure during this interval.";
          smiv2:max-access "read-only";
          smiv2:oid "1.3.6.1.4.1.9.9.657.1.4.1.14";
        }

        leaf csbHistoryStatsCallSetupCACPolicyFailure {
          type yang:gauge32;
          description
           "This object indicates the number of call setup failures due
            to CAC policy failure during this interval.";
          smiv2:max-access "read-only";
          smiv2:oid "1.3.6.1.4.1.9.9.657.1.4.1.15";
        }

        leaf csbHistoryStatsCallSetupCACCallLimitFailure {
          type yang:gauge32;
          description
           "This object indicates the number of call setup failures due
            to CAC call limit during this interval.";
          smiv2:max-access "read-only";
          smiv2:oid "1.3.6.1.4.1.9.9.657.1.4.1.16";
        }

        leaf csbHistoryStatsCallSetupCACRateLimitFailure {
          type yang:gauge32;
          description
           "This object indicates the number of call setup failures due
            to CAC call rate limit during this interval.";
          smiv2:max-access "read-only";
          smiv2:oid "1.3.6.1.4.1.9.9.657.1.4.1.17";
        }

        leaf csbHistoryStatsCallSetupCACBandwidthFailure {
          type yang:gauge32;
          description
           "This object indicates the number of call setup failures due
            to CAC bandwidth limit during this interval.";
          smiv2:max-access "read-only";
          smiv2:oid "1.3.6.1.4.1.9.9.657.1.4.1.18";
        }

        leaf csbHistoryStatsCallSetupCACMediaLimitFailure {
          type yang:gauge32;
          description
           "This object indicates the number of call setup failures due
            to CAC media limit during this interval.";
          smiv2:max-access "read-only";
          smiv2:oid "1.3.6.1.4.1.9.9.657.1.4.1.19";
        }

        leaf csbHistoryStatsCallSetupCACMediaUpdateFailure {
          type yang:gauge32;
          description
           "This object indicates the number of call update failure due
            to policy failure during this interval.";
          smiv2:max-access "read-only";
          smiv2:oid "1.3.6.1.4.1.9.9.657.1.4.1.20";
        }

        leaf csbHistoryStatsTimestamp {
          type binary {
            length "0..80";
          }
          description
           "This object indicates the time at the start of the interval
            when measurements were first collected for this interval in the
            csbCurrPeriodicStatsTable.";
          smiv2:max-access "read-only";
          smiv2:oid "1.3.6.1.4.1.9.9.657.1.4.1.21";
        }

        leaf csbHistroyStatsTranscodedCalls {
          type yang:gauge32;
          units "calls";
          description
           "The object indicates the number of active transcoded
            calls during this interval.";
          smiv2:max-access "read-only";
          smiv2:oid "1.3.6.1.4.1.9.9.657.1.4.1.22";
        }

        leaf csbHistroyStatsTransratedCalls {
          type yang:gauge32;
          units "calls";
          description
           "The object indicates the number of active transrated
            calls during this interval.";
          smiv2:max-access "read-only";
          smiv2:oid "1.3.6.1.4.1.9.9.657.1.4.1.23";
        }

        leaf csbHistoryStatsTotalCallUpdateFailure {
          type yang:gauge32;
          units "calls";
          description
           "This object indicates the total call update failures during
            this interval.";
          smiv2:max-access "read-only";
          smiv2:oid "1.3.6.1.4.1.9.9.657.1.4.1.24";
        }

        leaf csbHistoryStatsActiveIpv6Calls {
          type yang:gauge32;
          units "calls";
          description
           "This Object indicates the number of calls through SBC that use
            IPv6 signaling.  This statistic totals all calls that traverse
            an IPv6 adjacency on either or both sides of SBC during this
            interval.";
          smiv2:max-access "read-only";
          smiv2:oid "1.3.6.1.4.1.9.9.657.1.4.1.25";
        }

        leaf csbHistoryStatsActiveEmergencyCalls {
          type yang:gauge32;
          units "calls";
          description
           "This object indicates the number of calls through SBC that have
            been identified as emergency calls (by Number Analysis)  during
            this interval.";
          smiv2:max-access "read-only";
          smiv2:oid "1.3.6.1.4.1.9.9.657.1.4.1.26";
        }

        leaf csbHistoryStatsActiveE2EmergencyCalls {
          type yang:gauge32;
          units "calls";
          description
           "This object indicates the number of calls through SBC that have
            been identified as emergency calls (by Number Analysis) and
            have used the e2 interface to obtain location information for
            the
            caller.";
          smiv2:max-access "read-only";
          smiv2:oid "1.3.6.1.4.1.9.9.657.1.4.1.27";
        }

        leaf csbHistoryStatsImsRxActiveCalls {
          type yang:gauge32;
          units "calls";
          description
           "This object indicates the total number of active calls which
            use IMS Rx, during this interval.";
          smiv2:max-access "read-only";
          smiv2:oid "1.3.6.1.4.1.9.9.657.1.4.1.28";
        }

        leaf csbHistoryStatsImsRxCallSetupFailures {
          type yang:gauge32;
          units "failures";
          description
           "This object indicates the total call setup failures owing to
            IMS Rx failure during this interval.";
          smiv2:max-access "read-only";
          smiv2:oid "1.3.6.1.4.1.9.9.657.1.4.1.29";
        }

        leaf csbHistoryStatsImsRxCallRenegotiationAttempts {
          type yang:gauge32;
          units "attempts";
          description
           "This object indicates the total call renegotiation attempts
            using IMS Rx during this interval.";
          smiv2:max-access "read-only";
          smiv2:oid "1.3.6.1.4.1.9.9.657.1.4.1.30";
        }

        leaf csbHistoryStatsImsRxCallRenegotiationFailures {
          type yang:gauge32;
          units "failures";
          description
           "This object indicates the total call renegotiation failures
            owing to IMS Rx failure during this interval.";
          smiv2:max-access "read-only";
          smiv2:oid "1.3.6.1.4.1.9.9.657.1.4.1.31";
        }

        leaf csbHistoryStatsAudioTranscodedCalls {
          type yang:gauge32;
          units "calls";
          description
           "The number of active audio transcoded calls through
            this adjacency or account during this interval.";
          smiv2:max-access "read-only";
          smiv2:oid "1.3.6.1.4.1.9.9.657.1.4.1.32";
        }

        leaf csbHistoryStatsFaxTranscodedCalls {
          type yang:gauge32;
          units "calls";
          description
           "This object indicates the the number of active fax
            transcoded calls through this adjacency or account during this
            interval.";
          smiv2:max-access "read-only";
          smiv2:oid "1.3.6.1.4.1.9.9.657.1.4.1.33";
        }

        leaf csbHistoryStatsRtpDisallowedFailures {
          type yang:gauge32;
          units "failures";
          description
           "This object indicates the total call setup failures due to RTP
            being proposed when not permitted during this interval.";
          smiv2:max-access "read-only";
          smiv2:oid "1.3.6.1.4.1.9.9.657.1.4.1.34";
        }

        leaf csbHistoryStatsSrtpDisallowedFailures {
          type yang:gauge32;
          units "failures";
          description
           "This object indicates the total call setup failures due to SRTP
            being proposed when not permitted during this interval.";
          smiv2:max-access "read-only";
          smiv2:oid "1.3.6.1.4.1.9.9.657.1.4.1.35";
        }

        leaf csbHistoryStatsNonSrtpCalls {
          type yang:gauge32;
          units "calls";
          description
           "This object indicates the number of active calls
            through this adjacency or account which do not use SRTP on any
            media channels during this interval.";
          smiv2:max-access "read-only";
          smiv2:oid "1.3.6.1.4.1.9.9.657.1.4.1.36";
        }

        leaf csbHistoryStatsSrtpNonIwCalls {
          type yang:gauge32;
          units "calls";
          description
           "This object indicates the number of active calls
            through this adjacency or account that have one or more media
            channels that use SRTP but no media channels that provide
            interworking between RTP and SRTP during this interval.";
          smiv2:max-access "read-only";
          smiv2:oid "1.3.6.1.4.1.9.9.657.1.4.1.37";
        }

        leaf csbHistoryStatsSrtpIwCalls {
          type yang:gauge32;
          units "calls";
          description
           "This object indicates the number of active calls
            through this adjacency or account that have one or more media
            channels that provide interworking between RTP and SRTP during
            this interval.";
          smiv2:max-access "read-only";
          smiv2:oid "1.3.6.1.4.1.9.9.657.1.4.1.38";
        }

        leaf csbHistoryStatsDtmfIw2833Calls {
          type yang:gauge32;
          units "calls";
          description
           "This object indicates the number of active calls
            through this adjacency or account for which DTMF interworking
            is enabled between DTMF in signaling and DTMF in media via RFC
            2833 during this interval.";
          smiv2:max-access "read-only";
          smiv2:oid "1.3.6.1.4.1.9.9.657.1.4.1.39";
        }

        leaf csbHistoryStatsDtmfIwInbandCalls {
          type yang:gauge32;
          units "calls";
          description
           "This object indicates the number of active calls
            through this adjacency or account for which DTMF interworking
            is enabled between DTMF in signaling and DTMF in media via
            inband DTMF tones during this interval.";
          smiv2:max-access "read-only";
          smiv2:oid "1.3.6.1.4.1.9.9.657.1.4.1.40";
        }

        leaf csbHistoryStatsDtmfIw2833InbandCalls {
          type yang:gauge32;
          units "calls";
          description
           "This object indicates the number of active calls
            through this adjacency or account for which DTMF interworking
            is enabled between DTMF in media via RFC 2833 and DTMF in media
            via inband DTMF tones during this interval.";
          smiv2:max-access "read-only";
          smiv2:oid "1.3.6.1.4.1.9.9.657.1.4.1.41";
        }

        leaf csbHistoryStatsTotalTapsRequested {
          type yang:gauge32;
          units "attempts";
          description
           "This object indicates the lawful intercept tap attempts
            requested within the scope of this query during this interval.";
          smiv2:max-access "read-only";
          smiv2:oid "1.3.6.1.4.1.9.9.657.1.4.1.42";
        }

        leaf csbHistoryStatsTotalTapsSucceeded {
          type yang:gauge32;
          units "success";
          description
           "This object indicates the lawful intercept tap attempts that
            have been successfully implemented within the scope of this
            query during this interval.";
          smiv2:max-access "read-only";
          smiv2:oid "1.3.6.1.4.1.9.9.657.1.4.1.43";
        }

        leaf csbHistoryStatsCurrentTaps {
          type yang:gauge32;
          units "taps";
          description
           "This object indicates the Lawful intercept taps currently in
            place on calls within the scope of this query during this
            interval.";
          smiv2:max-access "read-only";
          smiv2:oid "1.3.6.1.4.1.9.9.657.1.4.1.44";
        }

        leaf csbHistoryStatsIpsecCalls {
          type yang:gauge32;
          units "calls";
          description
           "The number of active calls on this adjacency or account which
            are to or from registered subscribers using IPSEC during this
            interval.";
          smiv2:max-access "read-only";
          smiv2:oid "1.3.6.1.4.1.9.9.657.1.4.1.45";
        }
      }
    }

    container csbPerFlowStatsTable {
      description
       "This table describes statistics table for each call flow. The
        indices of the table are virtual media gateway id, gate id,
        falow pair id and side id (indices for side A or side B). The
        other indices of this table are csbCallStatsInstanceIndex
        defined in csbCallStatsInstanceTable and
        csbCallStatsServiceIndex defined in csbCallStatsTable.";
      smiv2:oid "1.3.6.1.4.1.9.9.657.1.5";

      list csbPerFlowStatsEntry {
        key "csbCallStatsInstanceIndex csbCallStatsServiceIndex csbPerFlowStatsVdbeId csbPerFlowStatsGateId csbPerFlowStatsFlowPairId csbPerFlowStatsSideId";
        description
         "An conceptual row in the csbPerFlowStatsTable. There is
          an entry in this table for vdbe Id, gate id, flow pair id and
          side id. The other indices of this table are
          csbCallStatsInstanceIndex defined in csbCallStatsInstanceTable
          and csbCallStatsServiceIndex defined in csbCallStatsTable.";
        smiv2:oid "1.3.6.1.4.1.9.9.657.1.5.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type leafref {
            path "/CISCO-SESS-BORDER-CTRLR-CALL-STATS-MIB:CISCO-SESS-BORDER-CTRLR-CALL-STATS-MIB/CISCO-SESS-BORDER-CTRLR-CALL-STATS-MIB:csbCallStatsTable/CISCO-SESS-BORDER-CTRLR-CALL-STATS-MIB:csbCallStatsEntry/CISCO-SESS-BORDER-CTRLR-CALL-STATS-MIB:csbCallStatsServiceIndex";
          }
        }

        leaf csbPerFlowStatsVdbeId {
          type int32 {
            range "0..255";
          }
          description
           "This object identifies the virtual media gateway id. This
            object also acts as an index for the table.";
          smiv2:max-access "not-accessible";
          smiv2:oid "1.3.6.1.4.1.9.9.657.1.5.1.1";
        }

        leaf csbPerFlowStatsGateId {
          type int32 {
            range "0..65535";
          }
          description
           "This object identifies the gate id. This object also acts as
            an index for the table.";
          smiv2:max-access "not-accessible";
          smiv2:oid "1.3.6.1.4.1.9.9.657.1.5.1.2";
        }

        leaf csbPerFlowStatsFlowPairId {
          type int32 {
            range "0..65535";
          }
          description
           "This object identifies the flow pair id. This object also acts
            as an index for the table.";
          smiv2:max-access "not-accessible";
          smiv2:oid "1.3.6.1.4.1.9.9.657.1.5.1.3";
        }

        leaf csbPerFlowStatsSideId {
          type enumeration {
            enum "sideA" {
              value "1";
            }
            enum "sideB" {
              value "2";
            }
          }
          description
           "This object identifies the index corresponding to side of flow
            pair either side A or side B. This object also acts as an index
            for the table.";
          smiv2:max-access "not-accessible";
          smiv2:oid "1.3.6.1.4.1.9.9.657.1.5.1.4";
        }

        leaf csbPerFlowStatsFlowType {
          type enumeration {
            enum "media" {
              value "1";
            }
            enum "signalling" {
              value "2";
            }
          }
          description
           "This object indicates the type of the flow, like media flow,
            signaling flow etc.";
          smiv2:max-access "read-only";
          smiv2:oid "1.3.6.1.4.1.9.9.657.1.5.1.5";
        }

        leaf csbPerFlowStatsRTPPktsSent {
          type yang:counter64;
          units "packets";
          description
           "This object indicates the number of RTP packets sent per flow
            by the SBC.";
          smiv2:max-access "read-only";
          smiv2:oid "1.3.6.1.4.1.9.9.657.1.5.1.6";
        }

        leaf csbPerFlowStatsRTPPktsRcvd {
          type yang:counter64;
          units "packets";
          description
           "This object indicates the number of RTP packets received per
            flow by the SBC.";
          smiv2:max-access "read-only";
          smiv2:oid "1.3.6.1.4.1.9.9.657.1.5.1.7";
        }

        leaf csbPerFlowStatsRTPPktsDiscard {
          type yang:counter64;
          units "packets";
          description
           "This object indicates the number of RTP packets discarded  per
            flow by the SBC.";
          smiv2:max-access "read-only";
          smiv2:oid "1.3.6.1.4.1.9.9.657.1.5.1.8";
        }

        leaf csbPerFlowStatsRTPOctetsSent {
          type yang:counter64;
          units "octets";
          description
           "This object indicates the number of RTP octets sent
            per flow by the SBC.";
          smiv2:max-access "read-only";
          smiv2:oid "1.3.6.1.4.1.9.9.657.1.5.1.9";
        }

        leaf csbPerFlowStatsRTPOctetsRcvd {
          type yang:counter64;
          units "octets";
          description
           "This object indicates the number of RTP octets received
            per flow by the SBC.";
          smiv2:max-access "read-only";
          smiv2:oid "1.3.6.1.4.1.9.9.657.1.5.1.10";
        }

        leaf csbPerFlowStatsRTPOctetsDiscard {
          type yang:counter64;
          units "octets";
          description
           "This object indicates the number of RTP octets discarded
            per flow by the SBC.";
          smiv2:max-access "read-only";
          smiv2:oid "1.3.6.1.4.1.9.9.657.1.5.1.11";
        }

        leaf csbPerFlowStatsRTCPPktsSent {
          type yang:counter64;
          units "packets";
          description
           "The number of RTP packets sent by the remote end point to this
            MG on this flow. Comparing this with the local number of RTP
            packets received from the remote end point gives an indication
            of how many incoming  packets were dropped on this leg of the
            call. This information is from RTCP packet. Not all endpoints
            report this statistic, if it is not available it will be set to
            zero. This statistic will not be available for signaling flows.";
          smiv2:max-access "read-only";
          smiv2:oid "1.3.6.1.4.1.9.9.657.1.5.1.12";
        }

        leaf csbPerFlowStatsRTCPPktsRcvd {
          type yang:counter64;
          units "packets";
          description
           "The number of RTP packets received by the remote end point from
            this MG on this flow. Comparing this with the local number of
            RTP packets sent from this MG to the remote endpoint gives an
            indication of how many outgoing packets were dropped on this
            leg of the call. This information is from RTCP packet. Not all
            endpoints report this statistic, if it is not available it will
            be set to zero. This statistic will not be available for
            signaling flows.";
          smiv2:max-access "read-only";
          smiv2:oid "1.3.6.1.4.1.9.9.657.1.5.1.13";
        }

        leaf csbPerFlowStatsRTCPPktsLost {
          type yang:counter64;
          units "packets";
          description
           "The number of RTP packets reported as lost by the remote end
            point on this flow. This information is from RTCP packet. Not
            all endpoints report this statistic, if it is not available it
            will be set to zero. This statistic will not be available for
            signaling flows.";
          smiv2:max-access "read-only";
          smiv2:oid "1.3.6.1.4.1.9.9.657.1.5.1.14";
        }

        leaf csbPerFlowStatsEPJitter {
          type yang:counter64;
          units "milliseconds";
          description
           "This object indicates the End Point jitter per flow in the
            SBC.";
          smiv2:max-access "read-only";
          smiv2:oid "1.3.6.1.4.1.9.9.657.1.5.1.15";
        }

        leaf csbPerFlowStatsTmanPerMbs {
          type yang:gauge32;
          units "bytes";
          description
           "This object indicates the maximum burst size for the
            current FlowPair.";
          smiv2:max-access "read-only";
          smiv2:oid "1.3.6.1.4.1.9.9.657.1.5.1.16";
        }

        leaf csbPerFlowStatsTmanPerSdr {
          type yang:gauge32;
          units "kilobytes per second";
          description
           "This object indicates the bandwidth reserved for flow in
            kilobytes/second.";
          smiv2:max-access "read-only";
          smiv2:oid "1.3.6.1.4.1.9.9.657.1.5.1.17";
        }

        leaf csbPerFlowStatsDscpSettings {
          type snmp-framework:SnmpAdminString;
          description
           "This object indicates the mark packets sent for the
            current FlowPair with, or zero if none set. The DSCP is a 6-bit
            value, which will be present in the top 6 bits of the lowest
            byte of this field.";
          smiv2:max-access "read-only";
          smiv2:oid "1.3.6.1.4.1.9.9.657.1.5.1.18";
        }

        leaf csbPerFlowStatsAdrStatus {
          type binary {
            length "0..10";
          }
          description
           "This object indicates whether the flow on the current
            FlowPair has subscribed for the NAT latch event.";
          smiv2:max-access "read-only";
          smiv2:oid "1.3.6.1.4.1.9.9.657.1.5.1.19";
        }

        leaf csbPerFlowStatsQASettings {
          type binary {
            length "0..10";
          }
          description
           "This object indicates the flow on the current FlowPair has
            subscribed for the media loss event.";
          smiv2:max-access "read-only";
          smiv2:oid "1.3.6.1.4.1.9.9.657.1.5.1.20";
        }

        leaf csbPerFlowStatsRTPPktsLost {
          type yang:counter64;
          units "packets";
          description
           "This object indicates the number of RTP packets lost per flow
            by the SBC.";
          smiv2:max-access "read-only";
          smiv2:oid "1.3.6.1.4.1.9.9.657.1.5.1.21";
        }
      }
    }

    container csbH248StatsTable {
      status deprecated;
      description
       "This table describes the H.248 statistics for SBC. The index of
        the table is service index which corresponds to a particular 
        service configured on the SBC and the index assigned to a
        particular H.248 controller. The other index of this table is
        csbCallStatsInstanceIndex defined in csbCallStatsInstanceTable.
        This table is replaced by the csbH248StatsRev1Table.";
      smiv2:oid "1.3.6.1.4.1.9.9.657.1.6";

      list csbH248StatsEntry {
        key "csbCallStatsInstanceIndex csbCallStatsServiceIndex csbH248StatsCtrlrIndex";
        status deprecated;
        description
         "An conceptual row in the csbCallStath248Table. There is
          an entry in this table for the particular controller by a value
          of csbH248StatsCtrlrIndex. The other indices of this table are
          csbCallStatsInstanceIndex defined in csbCallStatsInstanceTable
          and csbCallStatsServiceIndex defined in csbCallStatsTable.";
        smiv2:oid "1.3.6.1.4.1.9.9.657.1.6.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type leafref {
            path "/CISCO-SESS-BORDER-CTRLR-CALL-STATS-MIB:CISCO-SESS-BORDER-CTRLR-CALL-STATS-MIB/CISCO-SESS-BORDER-CTRLR-CALL-STATS-MIB:csbCallStatsTable/CISCO-SESS-BORDER-CTRLR-CALL-STATS-MIB:csbCallStatsEntry/CISCO-SESS-BORDER-CTRLR-CALL-STATS-MIB:csbCallStatsServiceIndex";
          }
        }

        leaf csbH248StatsCtrlrIndex {
          type int32 {
            range "1..50";
          }
          status deprecated;
          description
           "This object identifies the controller index of the H.248
            server. This is also the index for the table.";
          smiv2:max-access "not-accessible";
          smiv2:oid "1.3.6.1.4.1.9.9.657.1.6.1.1";
        }

        leaf csbH248StatsRequestsSent {
          type yang:counter32;
          status deprecated;
          description
           "This object indicates the requests sent through the Session
            Controller Interface to an SBE or DBE.";
          smiv2:max-access "read-only";
          smiv2:oid "1.3.6.1.4.1.9.9.657.1.6.1.2";
        }

        leaf csbH248StatsRequestsRcvd {
          type yang:counter32;
          status deprecated;
          description
           "This object indicates the requests received through the
            Session Controller Interface to an SBE or DBE.";
          smiv2:max-access "read-only";
          smiv2:oid "1.3.6.1.4.1.9.9.657.1.6.1.3";
        }

        leaf csbH248StatsRequestsFailed {
          type yang:counter32;
          status deprecated;
          description
           "This object indicates the requests failed on session
            Controller Interface to an SBE or DBE.";
          smiv2:max-access "read-only";
          smiv2:oid "1.3.6.1.4.1.9.9.657.1.6.1.4";
        }

        leaf csbH248StatsRequestsRetried {
          type yang:counter32;
          status deprecated;
          description
           "This object indicates the requests retried through the Session
            Controller Interface to an SBE or DBE.";
          smiv2:max-access "read-only";
          smiv2:oid "1.3.6.1.4.1.9.9.657.1.6.1.5";
        }

        leaf csbH248StatsRepliesSent {
          type yang:counter32;
          status deprecated;
          description
           "This object indicates the number of replies sent through the
            Session Controller Interface to an SBE or DBE.";
          smiv2:max-access "read-only";
          smiv2:oid "1.3.6.1.4.1.9.9.657.1.6.1.6";
        }

        leaf csbH248StatsRepliesRcvd {
          type yang:counter32;
          status deprecated;
          description
           "This object indicates the number of replies received from the
            Session Controller Interface to an SBE or DBE.";
          smiv2:max-access "read-only";
          smiv2:oid "1.3.6.1.4.1.9.9.657.1.6.1.7";
        }

        leaf csbH248StatsRepliesRetried {
          type yang:counter32;
          status deprecated;
          description
           "This object indicates the number of replies retried through
            the Session Controller Interface to an SBE or DBE.";
          smiv2:max-access "read-only";
          smiv2:oid "1.3.6.1.4.1.9.9.657.1.6.1.8";
        }

        leaf csbH248StatsSegPktsSent {
          type yang:counter32;
          status deprecated;
          description
           "This object indicates the number of packets sent through the
            Session Controller Interface to an SBE or DBE.";
          smiv2:max-access "read-only";
          smiv2:oid "1.3.6.1.4.1.9.9.657.1.6.1.9";
        }

        leaf csbH248StatsSegPktsRcvd {
          type yang:counter32;
          status deprecated;
          description
           "This object indicates the number of packets received from the
            Session Controller Interface to an SBE or DBE.";
          smiv2:max-access "read-only";
          smiv2:oid "1.3.6.1.4.1.9.9.657.1.6.1.10";
        }

        leaf csbH248StatsEstablishedTime {
          type binary {
            length "0..80";
          }
          status deprecated;
          description
           "This object indicates the H.248 Controller established
            time (the time at which the association became established).";
          smiv2:max-access "read-only";
          smiv2:oid "1.3.6.1.4.1.9.9.657.1.6.1.11";
        }

        leaf csbH248StatsTMaxTimeoutVal {
          type int32;
          units "milliseconds";
          status deprecated;
          description
           "This object indicates the T-Max timeout value. This field
            specifies the maximum delay (in milliseconds) for a response
            from an MGC before deciding that the request has failed.";
          smiv2:max-access "read-only";
          smiv2:oid "1.3.6.1.4.1.9.9.657.1.6.1.12";
        }

        leaf csbH248StatsRTT {
          type yang:gauge32;
          units "milliseconds";
          status deprecated;
          description
           "This object indicates the calculated RTT value. This field
            specifies the maximum round trip propagation delay in the 
            network (in milliseconds).";
          smiv2:max-access "read-only";
          smiv2:oid "1.3.6.1.4.1.9.9.657.1.6.1.13";
        }

        leaf csbH248StatsLT {
          type yang:gauge32;
          units "milliseconds";
          status deprecated;
          description
           "This object indicates the LT value calculated from RTT
            value and Max timeout value. This field specifies the maximum
            delay (in milliseconds) for a response from an MGC plus the
            maximum round trip propagation delay in the network (in
            milliseconds).";
          smiv2:max-access "read-only";
          smiv2:oid "1.3.6.1.4.1.9.9.657.1.6.1.14";
        }
      }
    }

    container csbH248StatsRev1Table {
      description
       "This table describes the H.248 statistics for SBC. The index of
        the table is service index which corresponds to a particular 
        service configured on the SBC and the index assigned to a
        particular H.248 controller. The other index of this table is
        csbCallStatsInstanceIndex defined in csbCallStatsInstanceTable.";
      smiv2:oid "1.3.6.1.4.1.9.9.657.1.7";

      list csbH248StatsRev1Entry {
        key "csbCallStatsInstanceIndex csbCallStatsServiceIndex csbH248StatsVdbeId";
        description
         "An conceptual row in the csbCallStath248Table. There is
          an entry in this table for the particular Vdbe by a value
          of csbH248StatsVdbeId. The other indices of this table are
          csbCallStatsInstanceIndex defined in csbCallStatsInstanceTable
          and csbCallStatsServiceIndex defined in csbCallStatsTable.";
        smiv2:oid "1.3.6.1.4.1.9.9.657.1.7.1";

        leaf csbCallStatsInstanceIndex {
          type leafref {
            path "/CISCO-SESS-BORDER-CTRLR-CALL-STATS-MIB:CISCO-SESS-BORDER-CTRLR-CALL-STATS-MIB/CISCO-SESS-BORDER-CTRLR-CALL-STATS-MIB:csbCallStatsInstanceTable/CISCO-SESS-BORDER-CTRLR-CALL-STATS-MIB:csbCallStatsInstanceEntry/CISCO-SESS-BORDER-CTRLR-CALL-STATS-MIB:csbCallStatsInstanceIndex";
          }
        }

        leaf csbCallStatsServiceIndex {
          type leafref {
            path "/CISCO-SESS-BORDER-CTRLR-CALL-STATS-MIB:CISCO-SESS-BORDER-CTRLR-CALL-STATS-MIB/CISCO-SESS-BORDER-CTRLR-CALL-STATS-MIB:csbCallStatsTable/CISCO-SESS-BORDER-CTRLR-CALL-STATS-MIB:csbCallStatsEntry/CISCO-SESS-BORDER-CTRLR-CALL-STATS-MIB:csbCallStatsServiceIndex";
          }
        }

        leaf csbH248StatsVdbeId {
          type int32 {
            range "0..255";
          }
          description
           "This object identifies the virtual media gateway id. This is
            also the index for the table.";
          smiv2:max-access "not-accessible";
          smiv2:oid "1.3.6.1.4.1.9.9.657.1.7.1.1";
        }

        leaf csbH248StatsRequestsSentRev1 {
          type yang:counter32;
          description
           "This object indicates the requests sent through the Session
            Controller Interface to an SBE or DBE.";
          smiv2:max-access "read-only";
          smiv2:oid "1.3.6.1.4.1.9.9.657.1.7.1.2";
        }

        leaf csbH248StatsRequestsRcvdRev1 {
          type yang:counter32;
          description
           "This object indicates the requests received through the
            Session Controller Interface to an SBE or DBE.";
          smiv2:max-access "read-only";
          smiv2:oid "1.3.6.1.4.1.9.9.657.1.7.1.3";
        }

        leaf csbH248StatsRequestsFailedRev1 {
          type yang:counter32;
          description
           "This object indicates the requests failed on session
            Controller Interface to an SBE or DBE.";
          smiv2:max-access "read-only";
          smiv2:oid "1.3.6.1.4.1.9.9.657.1.7.1.4";
        }

        leaf csbH248StatsRequestsRetriedRev1 {
          type yang:counter32;
          description
           "This object indicates the requests retried through the Session
            Controller Interface to an SBE or DBE.";
          smiv2:max-access "read-only";
          smiv2:oid "1.3.6.1.4.1.9.9.657.1.7.1.5";
        }

        leaf csbH248StatsRepliesSentRev1 {
          type yang:counter32;
          description
           "This object indicates the number of replies sent through the
            Session Controller Interface to an SBE or DBE.";
          smiv2:max-access "read-only";
          smiv2:oid "1.3.6.1.4.1.9.9.657.1.7.1.6";
        }

        leaf csbH248StatsRepliesRcvdRev1 {
          type yang:counter32;
          description
           "This object indicates the number of replies received from the
            Session Controller Interface to an SBE or DBE.";
          smiv2:max-access "read-only";
          smiv2:oid "1.3.6.1.4.1.9.9.657.1.7.1.7";
        }

        leaf csbH248StatsRepliesRetriedRev1 {
          type yang:counter32;
          description
           "This object indicates the number of replies retried through
            the Session Controller Interface to an SBE or DBE.";
          smiv2:max-access "read-only";
          smiv2:oid "1.3.6.1.4.1.9.9.657.1.7.1.8";
        }

        leaf csbH248StatsSegPktsSentRev1 {
          type yang:counter32;
          description
           "This object indicates the number of response segments sent by
            DBE. This field will only be present if segmentation is enabled
            on this association.";
          smiv2:max-access "read-only";
          smiv2:oid "1.3.6.1.4.1.9.9.657.1.7.1.9";
        }

        leaf csbH248StatsSegPktsRcvdRev1 {
          type yang:counter32;
          description
           "This object indicates the number of response segments received
            by DBE. This field will only be present if segmentation is
            enabled on this association.";
          smiv2:max-access "read-only";
          smiv2:oid "1.3.6.1.4.1.9.9.657.1.7.1.10";
        }

        leaf csbH248StatsEstablishedTimeRev1 {
          type binary {
            length "0..80";
          }
          description
           "This object indicates the H.248 Controller established
            time (the time at which the association became established).";
          smiv2:max-access "read-only";
          smiv2:oid "1.3.6.1.4.1.9.9.657.1.7.1.11";
        }

        leaf csbH248StatsTMaxTimeoutValRev1 {
          type int32;
          units "milliseconds";
          description
           "This object indicates the T-Max timeout value. This field
            specifies the maximum delay (in milliseconds) for a response
            from an MGC before deciding that the request has failed.";
          smiv2:max-access "read-only";
          smiv2:oid "1.3.6.1.4.1.9.9.657.1.7.1.12";
        }

        leaf csbH248StatsRTTRev1 {
          type yang:gauge32;
          units "milliseconds";
          description
           "This object indicates the calculated RTT value. This field
            specifies the maximum round trip propagation delay in the 
            network (in milliseconds).";
          smiv2:max-access "read-only";
          smiv2:oid "1.3.6.1.4.1.9.9.657.1.7.1.13";
        }

        leaf csbH248StatsLTRev1 {
          type yang:gauge32;
          units "milliseconds";
          description
           "This object indicates the LT value calculated from RTT
            value and Max timeout value. This field specifies the maximum
            delay (in milliseconds) for a response from an MGC plus the
            maximum round trip propagation delay in the network (in
            milliseconds).";
          smiv2:max-access "read-only";
          smiv2:oid "1.3.6.1.4.1.9.9.657.1.7.1.14";
        }
      }
    }
  }

  smiv2:alias "ciscoSbcCallStatsMIB" {
    smiv2:oid "1.3.6.1.4.1.9.9.657";
  }

  smiv2:alias "ciscoSbcCallStatsMIBNotifs" {
    smiv2:oid "1.3.6.1.4.1.9.9.657.0";
  }

  smiv2:alias "ciscoSbcCallStatsMIBObjects" {
    smiv2:oid "1.3.6.1.4.1.9.9.657.1";
  }

  smiv2:alias "ciscoSbcCallStatsMIBConform" {
    smiv2:oid "1.3.6.1.4.1.9.9.657.2";
  }

  smiv2:alias "csbCallStatsMIBCompliances" {
    smiv2:oid "1.3.6.1.4.1.9.9.657.2.1";
  }

  smiv2:alias "csbCallStatsMIBGroups" {
    smiv2:oid "1.3.6.1.4.1.9.9.657.2.2";
  }

}
