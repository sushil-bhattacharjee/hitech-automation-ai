module Cisco-IOS-XE-dialer-deviation {
  namespace "http://cisco.com/ns/yang/Cisco-IOS-XE-dialer-deviation";
  prefix ios-dialer-d;

  import Cisco-IOS-XE-native {
    prefix ios;
  }
  import Cisco-IOS-XE-dialer {
    prefix ios-dialer;
  }
  import cisco-semver {
    prefix cisco-semver;
  }

  organization
    "Cisco Systems";
  description
    "Cisco XE Native Deviation YANG module for IOS
     Copyright (c) 2020 by Cisco Systems, Inc.
     All rights reserved.";

  revision 2020-07-01 {
    description
      "Added dialer mtu deviation";
    cisco-semver:module-version "1.0.0";
  }

  deviation "/ios:native/ios:interface/ios:Dialer/ios:mtu" {
    deviate replace {
      type uint16 {
        range "64..9216";
      }
    }
  }
}
