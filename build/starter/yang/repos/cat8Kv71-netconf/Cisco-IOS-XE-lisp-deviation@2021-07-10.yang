module Cisco-IOS-XE-lisp-deviation {
  namespace "http://cisco.com/ns/yang/Cisco-IOS-XE-lisp-deviation";
  prefix ios-lisp-d;

  import Cisco-IOS-XE-native {
    prefix ios;
  }
  import Cisco-IOS-XE-lisp {
    prefix ios-lisp;
  }

  organization
    "Cisco Systems";
  description
    "Cisco XE Locator ID Separation Protocol (LISP) Deviation YANG module for IOS
     Copyright (c) 2021 by Cisco Systems, Inc.
     All rights reserved.";

  revision 2021-07-10 {
    description
      "Added tcp path-mtu-discovery deviation";
  }

  deviation "/ios:native/ios:router/ios-lisp:lisp/ios-lisp:tcp/ios-lisp:path-mtu-discovery" {
    deviate replace {
      default "false";
    }
  }

  deviation "/ios:native/ios:router/ios-lisp:lisp-list/ios-lisp:tcp/ios-lisp:path-mtu-discovery" {
    deviate replace {
      default "false";
    }
  }
}
