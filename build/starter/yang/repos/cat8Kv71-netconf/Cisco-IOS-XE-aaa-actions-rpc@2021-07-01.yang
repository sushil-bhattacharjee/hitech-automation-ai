module Cisco-IOS-XE-aaa-actions-rpc {
  yang-version 1;
  namespace "http://cisco.com/ns/yang/Cisco-IOS-XE-aaa-actions-rpc";
  prefix aaa-ios-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AAA RPC action data.
     Copyright (c) 2021 by Cisco Systems, Inc.
     All rights reserved.";

  revision 2021-07-01 {
    description
      "Initial revision";
    reference
      "1.0.0";
    cisco-semver:module-version "1.0.0";
  }

  typedef auth-test-mode {
    type enumeration {
      enum legacy-mode {
        value 0;
        description
          "Test the credentials using the legacy mode.";
      }
    }
    description
      "AAA test mode options";
  }

  grouping authentication-command {
    description
      "Parameters to execute the test aaa command.";
    leaf group-name {
      type string {
        length "1..256";
      }
      mandatory true;
      description
        "Server group name";
    }
    leaf username {
      type string {
        length "1..256";
      }
      mandatory true;
      description
        "Username to be tested";
    }
    leaf password {
      type string {
        length "1..256";
      }
      mandatory true;
      description
        "Password to be tested";
    }
    leaf mode {
      type aaa-ios-actions-rpc:auth-test-mode;
      mandatory true;
      description
        "Mode type to be used for testing";
    }
  }

  grouping auth-response {
    description
      "Response to test authentication request.";
    leaf id {
      type uint32;
      description
        "The ID is unique identifier generated per request. This is used
         in combination with event model, where event notification provides
         request specific ID in it. This is useful in matching a request
         with event notification.";
    }
  }

  rpc test-aaa-command {
    description
      "To test particular user credentials for a particular server group.
       The device sends a test authentication packet to the servers under
       the server group. The rpc returns with a 'id' if the operation
       was started successfully. Subscribe to the stream:test-aaa-authentication-update
       to receive the final authentication result.";
    input {
      uses aaa-ios-actions-rpc:authentication-command;
    }
    output {
      uses aaa-ios-actions-rpc:auth-response;
    }
  }
}
