module openconfig-aft-types {

  namespace "http://openconfig.net/yang/fib-types";
  prefix "oc-aftt";

  import openconfig-extensions { prefix "oc-ext"; }

  organization
    "OpenConfig Working Group";

  contact
    "OpenConfig Working Group
    www.openconfig.net";

  description
    "Types related to the OpenConfig Abstract Forwarding
    Table (AFT) model";

  oc-ext:openconfig-version "0.2.1";

  revision 2017-01-13 {
    description
      "Updated revision for external review";
    reference "0.2.1";
  }

  revision 2016-09-07 {
    description
      "Initial revision for external review";
    reference "0.2.0";
  }

  typedef encapsulation-header-type {
    type enumeration {
      enum GRE {
        description
          "The encapsulation header is a Generic Routing Encapsulation
          header.";
      }
      enum IPV4 {
        description
          "The encapsulation header is an IPv4 packet header";
      }
      enum IPV6 {
        description
          "The encapsulation header is an IPv6 packet header";
      }
      enum MPLS {
        description
          "The encapsulation header is one or more MPLS labels indicated
          by the pushed and popped label stack lists.";
      }
    }
    description
      "Types of tunnel encapsulation that are supported by systems as either
      head- or tail-end.";
  }

  identity AFT_ADDRESS_FAMILY {
    description
      "A base identity that is used for address families that have
      distinct Abstract Forwarding Tables (AFTs).";
  }

  identity IPV4_UNICAST {
    base AFT_ADDRESS_FAMILY;
    description
      "The AFT entries within the corresponding table relate to unicast
      IPv4 forwarding entries.";
  }

  identity IPV6_UNICAST {
    base AFT_ADDRESS_FAMILY;
    description
      "The AFT entries within the corresponding table relate to unicast
      IPv6 forwarding entries.";
  }

  identity MPLS {
    base AFT_ADDRESS_FAMILY;
    description
      "The AFT entries within the corresponding table relate to labelled
      forwarding entries using MPLS labels.";
  }

  identity L2_ETHERNET {
    base AFT_ADDRESS_FAMILY;
    description
      "The AFT entries within the corresponding table relate to Ethernet
      switched forwarding entries.";
  }
}
