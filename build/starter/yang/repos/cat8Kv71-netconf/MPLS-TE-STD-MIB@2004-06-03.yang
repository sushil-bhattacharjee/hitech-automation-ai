/*
 * Generated by confdc --mib2yang-std
 * Source: mgmt/dmi/model/mib/src/MPLS-TE-STD-MIB.mib
 */
/*
 * This YANG module has been generated by smidump 0.5.0:
 *
 *      smidump -f yang MPLS-TE-STD-MIB
 *
 * Do not edit. Edit the source file instead!
 */

module MPLS-TE-STD-MIB {

  namespace "urn:ietf:params:xml:ns:yang:smiv2:MPLS-TE-STD-MIB";
  prefix MPLS-TE-STD-MIB;

  import DIFFSERV-MIB {
    prefix "diffserv-mib";
  }

  import IF-MIB {
    prefix "if-mib";
  }

  import INET-ADDRESS-MIB {
    prefix "inet-address";
  }

  import MPLS-TC-STD-MIB {
    prefix "mpls-tc";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Multiprotocol Label Switching (MPLS) Working Group";

  contact
   "        Cheenu Srinivasan
    Bloomberg L.P.
    Email:  cheenu@bloomberg.net
    
    Arun Viswanathan
    Force10 Networks, Inc.
    Email:  arunv@force10networks.com
    
    Thomas D. Nadeau
    Cisco Systems, Inc.
    Email:  tnadeau@cisco.com
    
    Comments about this document should be emailed
    directly to the MPLS working group mailing list at
    mpls@uu.net.";

  description
   "Copyright (C) The Internet Society (2004). The
    initial version of this MIB module was published
    in RFC 3812. For full legal notices see the RFC
    itself or see: http://www.ietf.org/copyrights/ianamib.html
    
    This MIB module contains managed object definitions
     for MPLS Traffic Engineering (TE) as defined in:
    1. Extensions to RSVP for LSP Tunnels, Awduche et
     al, RFC 3209, December 2001
    2. Constraint-Based LSP Setup using LDP, Jamoussi
     (Editor), RFC 3212, January 2002
    3. Requirements for Traffic Engineering Over MPLS,
     Awduche, D., Malcolm, J., Agogbua, J., O'Dell, M.,
     and J. McManus, [RFC2702], September 1999";

  revision 2004-06-03 {
    description
     "Initial version issued as part of RFC 3812.";
  }


  container MPLS-TE-STD-MIB {
    config false;

    container mplsTeScalars {
      smiv2:oid "1.3.6.1.2.1.10.166.3.1";

      leaf mplsTunnelConfigured {
        type uint32;
        description
         "The number of tunnels configured on this device. A
          tunnel is considered configured if the
          mplsTunnelRowStatus is active(1).";
        smiv2:max-access "read-only";
        smiv2:oid "1.3.6.1.2.1.10.166.3.1.1";
      }

      leaf mplsTunnelActive {
        type uint32;
        description
         "The number of tunnels active on this device. A
          tunnel is considered active if the
          mplsTunnelOperStatus is up(1).";
        smiv2:max-access "read-only";
        smiv2:oid "1.3.6.1.2.1.10.166.3.1.2";
      }

      leaf mplsTunnelTEDistProto {
        type bits {
          bit other {
            position "0";
          }
          bit ospf {
            position "1";
          }
          bit isis {
            position "2";
          }
        }
        description
         "The traffic engineering distribution protocol(s)
          used by this LSR. Note that an LSR may support more
          than one distribution protocol simultaneously.";
        smiv2:max-access "read-only";
        smiv2:oid "1.3.6.1.2.1.10.166.3.1.3";
      }

      leaf mplsTunnelMaxHops {
        type uint32;
        description
         "The maximum number of hops that can be specified for
          a tunnel on this device.";
        smiv2:max-access "read-only";
        smiv2:oid "1.3.6.1.2.1.10.166.3.1.4";
      }

      leaf mplsTunnelNotificationMaxRate {
        type uint32;
        description
         "This variable indicates the maximum number of
          notifications issued per second. If events occur
          more rapidly, the implementation may simply fail to
          emit these notifications during that period, or may
          queue them until an appropriate time. A value of 0
          means no throttling is applied and events may be
          notified at the rate at which they occur.";
        smiv2:defval "0";
        smiv2:max-access "read-write";
        smiv2:oid "1.3.6.1.2.1.10.166.3.1.5";
      }
    }

    container mplsTeObjects {
      smiv2:oid "1.3.6.1.2.1.10.166.3.2";

      leaf mplsTunnelIndexNext {
        type diffserv-mib:IndexIntegerNextFree {
          range "0..65535";
        }
        description
         "This object contains an unused value for
          mplsTunnelIndex, or a zero to indicate
          that none exist. Negative values are not allowed,
          as they do not correspond to valid values of
          mplsTunnelIndex.
          
          Note that this object offers an unused value
          for an mplsTunnelIndex value at the ingress
          side of a tunnel. At other LSRs the value
          of mplsTunnelIndex SHOULD be taken from the
          value signaled by the MPLS signaling protocol.";
        smiv2:max-access "read-only";
        smiv2:oid "1.3.6.1.2.1.10.166.3.2.1";
      }

      leaf mplsTunnelHopListIndexNext {
        type mpls-tc:MplsPathIndexOrZero;
        description
         "This object contains an appropriate value to be used
          for mplsTunnelHopListIndex when creating entries in
          the mplsTunnelHopTable.  If the number of
          unassigned entries is exhausted, a retrieval
          operation will return a value of 0.  This object
          may also return a value of 0 when the LSR is unable
          to accept conceptual row creation, for example, if
          the mplsTunnelHopTable is implemented as read-only.
          To obtain the value of mplsTunnelHopListIndex for a
          new entry in the mplsTunnelHopTable, the manager
          issues a management protocol retrieval operation to
          obtain the current value of mplsTunnelHopIndex.
          
          When the SET is performed to create a row in the
          mplsTunnelHopTable, the Command Responder (agent)
          must determine whether the value is indeed still
          unused; Two Network Management Applications may
          attempt to create a row (configuration entry)
          simultaneously and use the same value. If it is
          currently unused, the SET succeeds and the Command
          Responder (agent) changes the value of this object,
          according to an implementation-specific algorithm.
          If the value is in use, however, the SET fails.  The
          Network Management Application must then re-read
          this variable to obtain a new usable value.";
        smiv2:max-access "read-only";
        smiv2:oid "1.3.6.1.2.1.10.166.3.2.3";
      }

      leaf mplsTunnelResourceIndexNext {
        type uint32 {
          range "0..2147483647";
        }
        description
         "This object contains the next appropriate value to
          be used for mplsTunnelResourceIndex when creating
          entries in the mplsTunnelResourceTable. If the
          number of unassigned entries is exhausted, a
          retrieval operation will return a value of 0.  This
          object may also return a value of 0 when the LSR is
          unable to accept conceptual row creation, for
          example, if the mplsTunnelTable is implemented as
          read-only.  To obtain the mplsTunnelResourceIndex
          value for a new entry, the manager must first issue
          a management protocol retrieval operation to obtain
          the current value of this object.
          
          When the SET is performed to create a row in the
          mplsTunnelResourceTable, the Command Responder
          (agent) must determine whether the value is indeed
          still unused; Two Network Management Applications
          may attempt to create a row (configuration entry)
          simultaneously and use the same value. If it is
          currently unused, the SET succeeds and the Command
          Responder (agent) changes the value of this object,
          according to an implementation-specific algorithm.
          If the value is in use, however, the SET fails.  The
          Network Management Application must then re-read
          this variable to obtain a new usable value.";
        smiv2:max-access "read-only";
        smiv2:oid "1.3.6.1.2.1.10.166.3.2.5";
      }

      leaf mplsTunnelNotificationEnable {
        type boolean;
        description
         "If this object is true, then it enables the
          generation of mplsTunnelUp and mplsTunnelDown
          traps, otherwise these traps are not emitted.";
        smiv2:defval "false";
        smiv2:max-access "read-write";
        smiv2:oid "1.3.6.1.2.1.10.166.3.2.11";
      }
    }

    container mplsTunnelTable {
      description
       "The mplsTunnelTable allows new MPLS tunnels to be
        created between an LSR and a remote endpoint, and
        existing tunnels to be reconfigured or removed.
        Note that only point-to-point tunnel segments are
        supported, although multipoint-to-point and point-
        to-multipoint connections are supported by an LSR
        acting as a cross-connect.  Each MPLS tunnel can
        thus have one out-segment originating at this LSR
        and/or one in-segment terminating at this LSR.";
      smiv2:oid "1.3.6.1.2.1.10.166.3.2.2";

      list mplsTunnelEntry {
        key "mplsTunnelIndex mplsTunnelInstance mplsTunnelIngressLSRId mplsTunnelEgressLSRId";
        description
         "An entry in this table represents an MPLS tunnel.
          An entry can be created by a network administrator
          or by an SNMP agent as instructed by an MPLS
          signalling protocol. Whenever a new entry is
          created with mplsTunnelIsIf set to true(1), then a
          corresponding entry is created in ifTable as well
          (see RFC 2863). The ifType of this entry is
          mplsTunnel(150).
          
          A tunnel entry needs to be uniquely identified across
          a MPLS network. Indices mplsTunnelIndex and
          mplsTunnelInstance uniquely identify a tunnel on
          the LSR originating the tunnel.  To uniquely
          identify a tunnel across an MPLS network requires
          index mplsTunnelIngressLSRId.  The last index
          mplsTunnelEgressLSRId is useful in identifying all
          instances of a tunnel that terminate on the same
          egress LSR.";
        reference
         "1. RFC 2863 - The Interfaces Group MIB, McCloghrie,
          K., and F. Kastenholtz, June 2000 ";
        smiv2:oid "1.3.6.1.2.1.10.166.3.2.2.1";

        leaf mplsTunnelIndex {
          type mpls-tc:MplsTunnelIndex;
          description
           "Uniquely identifies a set of tunnel instances
            between a pair of ingress and egress LSRs.
            Managers should obtain new values for row
            creation in this table by reading
            mplsTunnelIndexNext. When
            the MPLS signalling protocol is rsvp(2) this value
            SHOULD be equal to the value signaled in the
            Tunnel Id of the Session object. When the MPLS
            signalling protocol is crldp(3) this value
            SHOULD be equal to the value signaled in the
            LSP ID.";
          smiv2:max-access "not-accessible";
          smiv2:oid "1.3.6.1.2.1.10.166.3.2.2.1.1";
        }

        leaf mplsTunnelInstance {
          type mpls-tc:MplsTunnelInstanceIndex;
          description
           "Uniquely identifies a particular instance of a
            tunnel between a pair of ingress and egress LSRs.
            It is useful to identify multiple instances of
            tunnels for the purposes of backup and parallel
            tunnels. When the MPLS signaling protocol is
            rsvp(2) this value SHOULD be equal to the LSP Id
            of the Sender Template object. When the signaling
            protocol is crldp(3) there is no equivalent
            signaling object.";
          smiv2:max-access "not-accessible";
          smiv2:oid "1.3.6.1.2.1.10.166.3.2.2.1.2";
        }

        leaf mplsTunnelIngressLSRId {
          type mpls-tc:MplsExtendedTunnelId;
          description
           "Identity of the ingress LSR associated with this
            tunnel instance. When the MPLS signalling protocol
            is rsvp(2) this value SHOULD be equal to the Tunnel
            Sender Address in the Sender Template object and MAY
            be equal to the Extended Tunnel Id field in the
            SESSION object. When the MPLS signalling protocol is
            crldp(3) this value SHOULD be equal to the Ingress
            LSR Router ID field in the LSPID TLV object.";
          reference
           "1. RSVP-TE: Extensions to RSVP for LSP Tunnels,
            Awduche et al, RFC 3209, December 2001
            2. Constraint-Based LSP Setup using LDP, Jamoussi
            (Editor), RFC 3212, January 2002";
          smiv2:max-access "not-accessible";
          smiv2:oid "1.3.6.1.2.1.10.166.3.2.2.1.3";
        }

        leaf mplsTunnelEgressLSRId {
          type mpls-tc:MplsExtendedTunnelId;
          description
           "Identity of the egress LSR associated with this
            tunnel instance.";
          smiv2:max-access "not-accessible";
          smiv2:oid "1.3.6.1.2.1.10.166.3.2.2.1.4";
        }

        leaf mplsTunnelName {
          type snmp-framework:SnmpAdminString;
          description
           "The canonical name assigned to the tunnel. This name
            can be used to refer to the tunnel on the LSR's
            console port.  If mplsTunnelIsIf is set to true
            then the ifName of the interface corresponding to
            this tunnel should have a value equal to
            mplsTunnelName.  Also see the description of ifName
            in RFC 2863.";
          reference
           "RFC 2863 - The Interfaces Group MIB, McCloghrie, K.,
            and F. Kastenholtz, June 2000";
          smiv2:defval "";
          smiv2:max-access "read-write";
          smiv2:oid "1.3.6.1.2.1.10.166.3.2.2.1.5";
        }

        leaf mplsTunnelDescr {
          type snmp-framework:SnmpAdminString;
          description
           "A textual string containing information about the
            tunnel.  If there is no description this object
            contains a zero length string. This object is may
            not be signaled by MPLS signaling protocols,
            consequentally the value of this object at transit
            and egress LSRs MAY be automatically generated or
            absent.";
          smiv2:defval "";
          smiv2:max-access "read-write";
          smiv2:oid "1.3.6.1.2.1.10.166.3.2.2.1.6";
        }

        leaf mplsTunnelIsIf {
          type boolean;
          description
           "Denotes whether or not this tunnel corresponds to an
            interface represented in the interfaces group
            table. Note that if this variable is set to true
            then the ifName of the interface corresponding to
            this tunnel should have a value equal to
            mplsTunnelName.  Also see the description of ifName
            in RFC 2863.  This object is meaningful only at the
            ingress and egress LSRs.";
          reference
           "RFC 2863 - The Interfaces Group MIB, McCloghrie, K.,
            and F. Kastenholtz, June 2000";
          smiv2:defval "false";
          smiv2:max-access "read-write";
          smiv2:oid "1.3.6.1.2.1.10.166.3.2.2.1.7";
        }

        leaf mplsTunnelIfIndex {
          type if-mib:InterfaceIndexOrZero;
          description
           "If mplsTunnelIsIf is set to true, then this value
            contains the LSR-assigned ifIndex which corresponds
            to an entry in the interfaces table.  Otherwise
            this variable should contain the value of zero
            indicating that a valid ifIndex was not assigned to
            this tunnel interface.";
          reference
           "RFC 2863 - The Interfaces Group MIB, McCloghrie, K.,
            and F. Kastenholtz, June 2000";
          smiv2:defval "0";
          smiv2:max-access "read-only";
          smiv2:oid "1.3.6.1.2.1.10.166.3.2.2.1.8";
        }

        leaf mplsTunnelOwner {
          type mpls-tc:MplsOwner;
          description
           "Denotes the entity that created and is responsible
            for managing this tunnel. This column is
            automatically filled by the agent on creation of a
            row.";
          smiv2:max-access "read-only";
          smiv2:oid "1.3.6.1.2.1.10.166.3.2.2.1.9";
        }

        leaf mplsTunnelRole {
          type enumeration {
            enum "head" {
              value "1";
            }
            enum "transit" {
              value "2";
            }
            enum "tail" {
              value "3";
            }
            enum "headTail" {
              value "4";
            }
          }
          description
           "This value signifies the role that this tunnel
            entry/instance represents. This value MUST be set
            to head(1) at the originating point of the tunnel.
            This value MUST be set to transit(2) at transit
            points along the tunnel, if transit points are
            supported. This value MUST be set to tail(3) at the
            terminating point of the tunnel if tunnel tails are
            supported.
            
            The value headTail(4) is provided for tunnels that
            begin and end on the same LSR.";
          smiv2:defval "head";
          smiv2:max-access "read-write";
          smiv2:oid "1.3.6.1.2.1.10.166.3.2.2.1.10";
        }

        leaf mplsTunnelXCPointer {
          type snmpv2-tc:RowPointer;
          description
           "This variable points to a row in the mplsXCTable.
            This table identifies the segments that compose
            this tunnel, their characteristics, and
            relationships to each other. A value of zeroDotZero
            indicates that no LSP has been associated with this
            tunnel yet.";
          reference
           "Srinivasan, C., Viswanathan, A., and T. Nadeau,
            Multiprotocol Label Switching (MPLS) Label Switching
            Router (LSR) Management Information Base (MIB), RFC 3813,
            June 2004";
          smiv2:defval "zeroDotZero";
          smiv2:max-access "read-write";
          smiv2:oid "1.3.6.1.2.1.10.166.3.2.2.1.11";
        }

        leaf mplsTunnelSignallingProto {
          type enumeration {
            enum "none" {
              value "1";
            }
            enum "rsvp" {
              value "2";
            }
            enum "crldp" {
              value "3";
            }
            enum "other" {
              value "4";
            }
          }
          description
           "The signalling protocol, if any, used to setup this
            tunnel.";
          smiv2:defval "none";
          smiv2:max-access "read-write";
          smiv2:oid "1.3.6.1.2.1.10.166.3.2.2.1.12";
        }

        leaf mplsTunnelSetupPrio {
          type int32 {
            range "0..7";
          }
          description
           "Indicates the setup priority of this tunnel.";
          reference
           "1. RSVP-TE: Extensions to RSVP for LSP Tunnels,
            Awduche et al, RFC 3209, December 2001
            2. Constraint-Based LSP Setup using LDP, Jamoussi
            (Editor), RFC 3212, January 2002";
          smiv2:defval "0";
          smiv2:max-access "read-write";
          smiv2:oid "1.3.6.1.2.1.10.166.3.2.2.1.13";
        }

        leaf mplsTunnelHoldingPrio {
          type int32 {
            range "0..7";
          }
          description
           "Indicates the holding priority for this tunnel.";
          reference
           "1. RSVP-TE: Extensions to RSVP for LSP Tunnels,
            Awduche et al, RFC 3209, December 2001
            
            2. Constraint-Based LSP Setup using LDP, Jamoussi
            (Editor), RFC 3212, January 2002";
          smiv2:defval "0";
          smiv2:max-access "read-write";
          smiv2:oid "1.3.6.1.2.1.10.166.3.2.2.1.14";
        }

        leaf mplsTunnelSessionAttributes {
          type bits {
            bit fastReroute {
              position "0";
            }
            bit mergingPermitted {
              position "1";
            }
            bit isPersistent {
              position "2";
            }
            bit isPinned {
              position "3";
            }
            bit recordRoute {
              position "4";
            }
          }
          description
           "This bit mask indicates optional session values for
            this tunnel. The following describes these bit
            fields:
            
            fastRerouteThis flag indicates that the any tunnel
            hop may choose to reroute this tunnel without
            tearing it down.  This flag permits transit routers
            to use a local repair mechanism which may result in
            violation of the explicit routing of this tunnel.
            When a fault is detected on an adjacent downstream
            link or node, a transit router can re-route traffic
            for fast service restoration.
            
            mergingPermitted This flag permits transit routers
            to merge this session with other RSVP sessions for
            the purpose of reducing resource overhead on
            downstream transit routers, thereby providing
            better network scaling.
            
            isPersistent  Indicates whether this tunnel should
            be restored automatically after a failure occurs.
            
            isPinned   This flag indicates whether the loose-
            routed hops of this tunnel are to be pinned.
            
            recordRouteThis flag indicates whether or not the
            signalling protocol should remember the tunnel path
            after it has been signaled.";
          reference
           "1. RSVP-TE: Extensions to RSVP for LSP Tunnels,
            Awduche et al, RFC 3209, December 2001.";
          smiv2:max-access "read-write";
          smiv2:oid "1.3.6.1.2.1.10.166.3.2.2.1.15";
        }

        leaf mplsTunnelLocalProtectInUse {
          type boolean;
          description
           "Indicates that the local repair mechanism is in use
            to maintain this tunnel (usually in the face of an
            outage of the link it was previously routed over).";
          smiv2:defval "false";
          smiv2:max-access "read-write";
          smiv2:oid "1.3.6.1.2.1.10.166.3.2.2.1.16";
        }

        leaf mplsTunnelResourcePointer {
          type snmpv2-tc:RowPointer;
          description
           "This variable represents a pointer to the traffic
            parameter specification for this tunnel.  This
            value may point at an entry in the
            mplsTunnelResourceEntry to indicate which
            mplsTunnelResourceEntry is to be assigned to this
            LSP instance.  This value may optionally point at
            an externally defined traffic parameter
            specification table.  A value of zeroDotZero
            indicates best-effort treatment.  By having the
            same value of this object, two or more LSPs can
            indicate resource sharing.";
          smiv2:defval "zeroDotZero";
          smiv2:max-access "read-write";
          smiv2:oid "1.3.6.1.2.1.10.166.3.2.2.1.17";
        }

        leaf mplsTunnelPrimaryInstance {
          type mpls-tc:MplsTunnelInstanceIndex;
          description
           "Specifies the instance index of the primary instance
            of this tunnel. More details of the definition of
            tunnel instances and the primary tunnel instance
            can be found in the description of the TEXTUAL-CONVENTION
            MplsTunnelInstanceIndex.";
          smiv2:defval "0";
          smiv2:max-access "read-only";
          smiv2:oid "1.3.6.1.2.1.10.166.3.2.2.1.18";
        }

        leaf mplsTunnelInstancePriority {
          type uint32;
          description
           "This value indicates which priority, in descending
            order, with 0 indicating the lowest priority,
            within a group of tunnel instances. A group of
            tunnel instances is defined as a set of LSPs with
            the same mplsTunnelIndex in this table, but with a
            different mplsTunnelInstance. Tunnel instance
            priorities are used to denote the priority at which
            a particular tunnel instance will supercede
            another. Instances of tunnels containing the same
            mplsTunnelInstancePriority will be used for load
            sharing.";
          smiv2:defval "0";
          smiv2:max-access "read-write";
          smiv2:oid "1.3.6.1.2.1.10.166.3.2.2.1.19";
        }

        leaf mplsTunnelHopTableIndex {
          type mpls-tc:MplsPathIndexOrZero;
          description
           "Index into the mplsTunnelHopTable entry that
            specifies the explicit route hops for this tunnel.
            This object is meaningful only at the head-end of
            the tunnel.";
          smiv2:defval "0";
          smiv2:max-access "read-write";
          smiv2:oid "1.3.6.1.2.1.10.166.3.2.2.1.20";
        }

        leaf mplsTunnelPathInUse {
          type mpls-tc:MplsPathIndexOrZero;
          description
           "This value denotes the configured path that was
            chosen for this tunnel. This value reflects the
            secondary index into mplsTunnelHopTable. This path
            may not exactly match the one in
            mplsTunnelARHopTable due to the fact that some CSPF
            modification may have taken place. See
            mplsTunnelARHopTable for the actual path being
            taken by the tunnel. A value of zero denotes that
            no path is currently in use or available.";
          smiv2:defval "0";
          smiv2:max-access "read-write";
          smiv2:oid "1.3.6.1.2.1.10.166.3.2.2.1.21";
        }

        leaf mplsTunnelARHopTableIndex {
          type mpls-tc:MplsPathIndexOrZero;
          description
           "Index into the mplsTunnelARHopTable entry that
            specifies the actual hops traversed by the tunnel.
            This is automatically updated by the agent when the
            actual hops becomes available.";
          smiv2:defval "0";
          smiv2:max-access "read-only";
          smiv2:oid "1.3.6.1.2.1.10.166.3.2.2.1.22";
        }

        leaf mplsTunnelCHopTableIndex {
          type mpls-tc:MplsPathIndexOrZero;
          description
           "Index into the mplsTunnelCHopTable entry that
            specifies the computed hops traversed by the
            tunnel. This is automatically updated by the agent
            when computed hops become available or when
            computed hops get modified.";
          smiv2:defval "0";
          smiv2:max-access "read-only";
          smiv2:oid "1.3.6.1.2.1.10.166.3.2.2.1.23";
        }

        leaf mplsTunnelIncludeAnyAffinity {
          type mpls-tc:MplsTunnelAffinity;
          description
           "A link satisfies the include-any constraint if and
            only if the constraint is zero, or the link and the
            constraint have a resource class in common.";
          reference
           "1. RSVP-TE: Extensions to RSVP for LSP Tunnels,
            Awduche et al, RFC 3209, December 2001.";
          smiv2:max-access "read-write";
          smiv2:oid "1.3.6.1.2.1.10.166.3.2.2.1.24";
        }

        leaf mplsTunnelIncludeAllAffinity {
          type mpls-tc:MplsTunnelAffinity;
          description
           "A link satisfies the include-all constraint if and
            only if the link contains all of the administrative
            groups specified in the constraint.";
          reference
           "1. RSVP-TE: Extensions to RSVP for LSP Tunnels,
            Awduche et al, RFC 3209, December 2001.";
          smiv2:max-access "read-write";
          smiv2:oid "1.3.6.1.2.1.10.166.3.2.2.1.25";
        }

        leaf mplsTunnelExcludeAnyAffinity {
          type mpls-tc:MplsTunnelAffinity;
          description
           "A link satisfies the exclude-any constraint if and
            only if the link contains none of the
            administrative groups specified in the constraint.";
          reference
           "1. RSVP-TE: Extensions to RSVP for LSP Tunnels,
            Awduche et al, RFC 3209, December 2001.";
          smiv2:defval "0";
          smiv2:max-access "read-write";
          smiv2:oid "1.3.6.1.2.1.10.166.3.2.2.1.26";
        }

        leaf mplsTunnelTotalUpTime {
          type yang:timeticks;
          description
           "This value represents the aggregate up time for all
            instances of this tunnel, if available. If this
            value is unavailable, it MUST return a value of 0.";
          smiv2:max-access "read-only";
          smiv2:oid "1.3.6.1.2.1.10.166.3.2.2.1.27";
        }

        leaf mplsTunnelInstanceUpTime {
          type yang:timeticks;
          description
           "This value identifies the total time that this
            tunnel instance's operStatus has been Up(1).";
          smiv2:max-access "read-only";
          smiv2:oid "1.3.6.1.2.1.10.166.3.2.2.1.28";
        }

        leaf mplsTunnelPrimaryUpTime {
          type yang:timeticks;
          description
           "Specifies the total time the primary instance of
            this tunnel has been active. The primary instance
            of this tunnel is defined in
            mplsTunnelPrimaryInstance.";
          smiv2:max-access "read-only";
          smiv2:oid "1.3.6.1.2.1.10.166.3.2.2.1.29";
        }

        leaf mplsTunnelPathChanges {
          type yang:counter32;
          description
           "Specifies the number of times the actual path for
            this tunnel instance has changed.";
          smiv2:max-access "read-only";
          smiv2:oid "1.3.6.1.2.1.10.166.3.2.2.1.30";
        }

        leaf mplsTunnelLastPathChange {
          type yang:timeticks;
          description
           "Specifies the time since the last change to the
            actual path for this tunnel instance.";
          smiv2:max-access "read-only";
          smiv2:oid "1.3.6.1.2.1.10.166.3.2.2.1.31";
        }

        leaf mplsTunnelCreationTime {
          type yang:timestamp;
          description
           "Specifies the value of SysUpTime when the first
            instance of this tunnel came into existence.
            That is, when the value of mplsTunnelOperStatus
            was first set to up(1).";
          smiv2:max-access "read-only";
          smiv2:oid "1.3.6.1.2.1.10.166.3.2.2.1.32";
        }

        leaf mplsTunnelStateTransitions {
          type yang:counter32;
          description
           "Specifies the number of times the state
            (mplsTunnelOperStatus) of this tunnel instance has
            changed.";
          smiv2:max-access "read-only";
          smiv2:oid "1.3.6.1.2.1.10.166.3.2.2.1.33";
        }

        leaf mplsTunnelAdminStatus {
          type enumeration {
            enum "up" {
              value "1";
            }
            enum "down" {
              value "2";
            }
            enum "testing" {
              value "3";
            }
          }
          description
           "Indicates the desired operational status of this
            tunnel.";
          smiv2:max-access "read-write";
          smiv2:oid "1.3.6.1.2.1.10.166.3.2.2.1.34";
        }

        leaf mplsTunnelOperStatus {
          type enumeration {
            enum "up" {
              value "1";
            }
            enum "down" {
              value "2";
            }
            enum "testing" {
              value "3";
            }
            enum "unknown" {
              value "4";
            }
            enum "dormant" {
              value "5";
            }
            enum "notPresent" {
              value "6";
            }
            enum "lowerLayerDown" {
              value "7";
            }
          }
          description
           "Indicates the actual operational status of this
            tunnel, which is typically but not limited to, a
            function of the state of individual segments of
            this tunnel.";
          smiv2:max-access "read-only";
          smiv2:oid "1.3.6.1.2.1.10.166.3.2.2.1.35";
        }

        leaf mplsTunnelRowStatus {
          type snmpv2-tc:RowStatus;
          description
           "This variable is used to create, modify, and/or
            delete a row in this table.  When a row in this
            table is in active(1) state, no objects in that row
            can be modified by the agent except
            mplsTunnelAdminStatus, mplsTunnelRowStatus and
            mplsTunnelStorageType.";
          smiv2:max-access "read-write";
          smiv2:oid "1.3.6.1.2.1.10.166.3.2.2.1.36";
        }

        leaf mplsTunnelStorageType {
          type snmpv2-tc:StorageType;
          description
           "The storage type for this tunnel entry.
            Conceptual rows having the value 'permanent'
            need not allow write-access to any columnar
            objects in the row.";
          smiv2:defval "volatile";
          smiv2:max-access "read-write";
          smiv2:oid "1.3.6.1.2.1.10.166.3.2.2.1.37";
        }
      }
    }

    container mplsTunnelHopTable {
      description
       "The mplsTunnelHopTable is used to indicate the hops,
        strict or loose, for an instance of an MPLS tunnel
        defined in mplsTunnelTable, when it is established
        via signalling, for the outgoing direction of the
        tunnel. Thus at a transit LSR, this table contains
        the desired path of the tunnel from this LSR
        onwards. Each row in this table is indexed by
        mplsTunnelHopListIndex which corresponds to a group
        of hop lists or path options.  Each row also has a
        secondary index mplsTunnelHopIndex, which indicates
        a group of hops (also known as a path option).
        Finally, the third index, mplsTunnelHopIndex
        indicates the specific hop information for a path
        option. In case we want to specify a particular
        interface on the originating LSR of an outgoing
        tunnel by which we want packets to exit the LSR,
        we specify this as the first hop for this tunnel in
        mplsTunnelHopTable.";
      smiv2:oid "1.3.6.1.2.1.10.166.3.2.4";

      list mplsTunnelHopEntry {
        key "mplsTunnelHopListIndex mplsTunnelHopPathOptionIndex mplsTunnelHopIndex";
        description
         "An entry in this table represents a tunnel hop.  An
          entry is created by a network administrator for
          signaled ERLSP set up by an MPLS signalling
          protocol.";
        smiv2:oid "1.3.6.1.2.1.10.166.3.2.4.1";

        leaf mplsTunnelHopListIndex {
          type mpls-tc:MplsPathIndex;
          description
           "Primary index into this table identifying a
            particular explicit route object.";
          smiv2:max-access "not-accessible";
          smiv2:oid "1.3.6.1.2.1.10.166.3.2.4.1.1";
        }

        leaf mplsTunnelHopPathOptionIndex {
          type mpls-tc:MplsPathIndex;
          description
           "Secondary index into this table identifying a
            particular group of hops representing a particular
            configured path. This is otherwise known as a path
            option.";
          smiv2:max-access "not-accessible";
          smiv2:oid "1.3.6.1.2.1.10.166.3.2.4.1.2";
        }

        leaf mplsTunnelHopIndex {
          type mpls-tc:MplsPathIndex;
          description
           "Tertiary index into this table identifying a
            particular hop.";
          smiv2:max-access "not-accessible";
          smiv2:oid "1.3.6.1.2.1.10.166.3.2.4.1.3";
        }

        leaf mplsTunnelHopAddrType {
          type mpls-tc:TeHopAddressType;
          description
           "The Hop Address Type of this tunnel hop.
            
            The value of this object cannot be changed
            if the value of the corresponding
            mplsTunnelHopRowStatus object is 'active'.
            
            Note that lspid(5) is a valid option only
            for tunnels signaled via CRLDP.";
          smiv2:defval "ipv4";
          smiv2:max-access "read-write";
          smiv2:oid "1.3.6.1.2.1.10.166.3.2.4.1.4";
        }

        leaf mplsTunnelHopIpAddr {
          type mpls-tc:TeHopAddress;
          description
           "The Tunnel Hop Address for this tunnel hop.
            
            The type of this address is determined by the
            value of the corresponding mplsTunnelHopAddrType.
            
            The value of this object cannot be changed
            if the value of the corresponding
            mplsTunnelHopRowStatus object is 'active'.";
          smiv2:defval "'00000000'H";
          smiv2:max-access "read-write";
          smiv2:oid "1.3.6.1.2.1.10.166.3.2.4.1.5";
        }

        leaf mplsTunnelHopIpPrefixLen {
          type inet-address:InetAddressPrefixLength;
          description
           "If mplsTunnelHopAddrType is set to ipv4(1) or
            ipv6(2), then this value will contain an
            appropriate prefix length for the IP address in
            object mplsTunnelHopIpAddr. Otherwise this value
            is irrelevant and should be ignored.";
          smiv2:defval "32";
          smiv2:max-access "read-write";
          smiv2:oid "1.3.6.1.2.1.10.166.3.2.4.1.6";
        }

        leaf mplsTunnelHopAsNumber {
          type mpls-tc:TeHopAddressAS;
          description
           "If mplsTunnelHopAddrType is set to asnumber(3), then
            this value will contain the AS number of this hop.
            Otherwise the agent should set this object to zero-
            length string and the manager should ignore this.";
          smiv2:max-access "read-write";
          smiv2:oid "1.3.6.1.2.1.10.166.3.2.4.1.7";
        }

        leaf mplsTunnelHopAddrUnnum {
          type mpls-tc:TeHopAddressUnnum;
          description
           "If mplsTunnelHopAddrType is set to unnum(4), then
            this value will contain the interface identifier of
            the unnumbered interface for this hop. This object
            should be used in conjunction with
            mplsTunnelHopIpAddress which would contain the LSR
            Router ID in this case. Otherwise the agent should
            set this object to zero-length string and the
            manager should ignore this.";
          smiv2:max-access "read-write";
          smiv2:oid "1.3.6.1.2.1.10.166.3.2.4.1.8";
        }

        leaf mplsTunnelHopLspId {
          type mpls-tc:MplsLSPID;
          description
           "If mplsTunnelHopAddrType is set to lspid(5), then
            this value will contain the LSPID of a tunnel of
            this hop. The present tunnel being configured is
            tunneled through this hop (using label stacking).
            This object is otherwise insignificant and should
            contain a value of 0 to indicate this fact.";
          smiv2:max-access "read-write";
          smiv2:oid "1.3.6.1.2.1.10.166.3.2.4.1.9";
        }

        leaf mplsTunnelHopType {
          type enumeration {
            enum "strict" {
              value "1";
            }
            enum "loose" {
              value "2";
            }
          }
          description
           "Denotes whether this tunnel hop is routed in a
            strict or loose fashion. The value of this object
            has no meaning if the mplsTunnelHopInclude object
            is set to 'false'.";
          smiv2:max-access "read-write";
          smiv2:oid "1.3.6.1.2.1.10.166.3.2.4.1.10";
        }

        leaf mplsTunnelHopInclude {
          type boolean;
          description
           "If this value is set to true, then this indicates
            that this hop must be included in the tunnel's
            path. If this value is set to 'false', then this hop
            must be avoided when calculating the path for this
            tunnel. The default value of this object is 'true',
            so that by default all indicated hops are included
            in the CSPF path computation. If this object is set
            to 'false' the value of mplsTunnelHopType should be
            ignored.";
          smiv2:defval "true";
          smiv2:max-access "read-write";
          smiv2:oid "1.3.6.1.2.1.10.166.3.2.4.1.11";
        }

        leaf mplsTunnelHopPathOptionName {
          type snmp-framework:SnmpAdminString;
          description
           "The description of this series of hops as they
            relate to the specified path option. The
            value of this object SHOULD be the same for
            each hop in the series that comprises a
            path option.";
          smiv2:max-access "read-write";
          smiv2:oid "1.3.6.1.2.1.10.166.3.2.4.1.12";
        }

        leaf mplsTunnelHopEntryPathComp {
          type enumeration {
            enum "dynamic" {
              value "1";
            }
            enum "explicit" {
              value "2";
            }
          }
          description
           "If this value is set to dynamic, then the user
            should only specify the source and destination of
            the path and expect that the CSPF will calculate
            the remainder of the path.  If this value is set to
            explicit, the user should specify the entire path
            for the tunnel to take.  This path may contain
            strict or loose hops.  Each hop along a specific
            path SHOULD have this object set to the same value";
          smiv2:max-access "read-write";
          smiv2:oid "1.3.6.1.2.1.10.166.3.2.4.1.13";
        }

        leaf mplsTunnelHopRowStatus {
          type snmpv2-tc:RowStatus;
          description
           "This variable is used to create, modify, and/or
            delete a row in this table.  When a row in this
            table is in active(1) state, no objects in that row
            can be modified by the agent except
            mplsTunnelHopRowStatus and
            mplsTunnelHopStorageType.";
          smiv2:max-access "read-write";
          smiv2:oid "1.3.6.1.2.1.10.166.3.2.4.1.14";
        }

        leaf mplsTunnelHopStorageType {
          type snmpv2-tc:StorageType;
          description
           "The storage type for this Hop entry. Conceptual
            rows having the value 'permanent' need not
            allow write-access to any columnar objects
            in the row.";
          smiv2:defval "volatile";
          smiv2:max-access "read-write";
          smiv2:oid "1.3.6.1.2.1.10.166.3.2.4.1.15";
        }
      }
    }

    container mplsTunnelResourceTable {
      description
       "The mplsTunnelResourceTable allows a manager to
        specify which resources are desired for an MPLS
        tunnel.  This table also allows several tunnels to
        point to a single entry in this table, implying
        that these tunnels should share resources.";
      smiv2:oid "1.3.6.1.2.1.10.166.3.2.6";

      list mplsTunnelResourceEntry {
        key "mplsTunnelResourceIndex";
        description
         "An entry in this table represents a set of resources
          for an MPLS tunnel.  An entry can be created by a
          network administrator or by an SNMP agent as
          instructed by any MPLS signalling protocol.
          An entry in this table referenced by a tunnel instance
          with zero mplsTunnelInstance value indicates a
          configured set of resource parameter. An entry
          referenced by a tunnel instance with a non-zero
          mplsTunnelInstance reflects the in-use resource
          parameters for the tunnel instance which may have
          been negotiated or modified by the MPLS signaling
          protocols.";
        smiv2:oid "1.3.6.1.2.1.10.166.3.2.6.1";

        leaf mplsTunnelResourceIndex {
          type uint32 {
            range "1..2147483647";
          }
          description
           "Uniquely identifies this row.";
          smiv2:max-access "not-accessible";
          smiv2:oid "1.3.6.1.2.1.10.166.3.2.6.1.1";
        }

        leaf mplsTunnelResourceMaxRate {
          type mpls-tc:MplsBitRate;
          units "kilobits per second";
          description
           "The maximum rate in bits/second.  Note that setting
            mplsTunnelResourceMaxRate,
            mplsTunnelResourceMeanRate, and
            mplsTunnelResourceMaxBurstSize to 0 indicates best-
            effort treatment.";
          smiv2:max-access "read-write";
          smiv2:oid "1.3.6.1.2.1.10.166.3.2.6.1.2";
        }

        leaf mplsTunnelResourceMeanRate {
          type mpls-tc:MplsBitRate;
          units "kilobits per second";
          description
           "This object is copied into an instance of
            mplsTrafficParamMeanRate in the
            mplsTrafficParamTable. The OID of this table entry
            is then copied into the corresponding
            mplsInSegmentTrafficParamPtr.";
          smiv2:max-access "read-write";
          smiv2:oid "1.3.6.1.2.1.10.166.3.2.6.1.3";
        }

        leaf mplsTunnelResourceMaxBurstSize {
          type mpls-tc:MplsBurstSize;
          units "bytes";
          description
           "The maximum burst size in bytes.";
          smiv2:max-access "read-write";
          smiv2:oid "1.3.6.1.2.1.10.166.3.2.6.1.4";
        }

        leaf mplsTunnelResourceMeanBurstSize {
          type mpls-tc:MplsBurstSize;
          units "bytes";
          description
           "The mean burst size in bytes.  The implementations
            which do not implement this variable must return
            a noSuchObject exception for this object and must
            not allow a user to set this object.";
          smiv2:max-access "read-write";
          smiv2:oid "1.3.6.1.2.1.10.166.3.2.6.1.5";
        }

        leaf mplsTunnelResourceExBurstSize {
          type mpls-tc:MplsBurstSize;
          units "bytes";
          description
           "The Excess burst size in bytes.  The implementations
            which do not implement this variable must return
            noSuchObject exception for this object and must
            not allow a user to set this value.";
          reference
           "CR-LDP Specification, Section 4.3.";
          smiv2:max-access "read-write";
          smiv2:oid "1.3.6.1.2.1.10.166.3.2.6.1.6";
        }

        leaf mplsTunnelResourceFrequency {
          type enumeration {
            enum "unspecified" {
              value "1";
            }
            enum "frequent" {
              value "2";
            }
            enum "veryFrequent" {
              value "3";
            }
          }
          description
           "The granularity of the availability of committed
            rate.  The implementations which do not implement
            this variable must return unspecified(1) for this
            value and must not allow a user to set this value.";
          reference
           "CR-LDP Specification, Section 4.3.";
          smiv2:max-access "read-write";
          smiv2:oid "1.3.6.1.2.1.10.166.3.2.6.1.7";
        }

        leaf mplsTunnelResourceWeight {
          type uint32 {
            range "0..255";
          }
          description
           "The relative weight for using excess bandwidth above
            its committed rate.  The value of 0 means that
            weight is not applicable for the CR-LSP.";
          reference
           "CR-LDP Specification, Section 4.3.";
          smiv2:max-access "read-write";
          smiv2:oid "1.3.6.1.2.1.10.166.3.2.6.1.8";
        }

        leaf mplsTunnelResourceRowStatus {
          type snmpv2-tc:RowStatus;
          description
           "This variable is used to create, modify, and/or
            delete a row in this table.  When a row in this
            table is in active(1) state, no objects in that row
            can be modified by the agent except
            mplsTunnelResourceRowStatus and
            mplsTunnelResourceStorageType.";
          smiv2:max-access "read-write";
          smiv2:oid "1.3.6.1.2.1.10.166.3.2.6.1.9";
        }

        leaf mplsTunnelResourceStorageType {
          type snmpv2-tc:StorageType;
          description
           "The storage type for this Hop entry. Conceptual
            rows having the value 'permanent' need not
            allow write-access to any columnar objects
            in the row.";
          smiv2:defval "volatile";
          smiv2:max-access "read-write";
          smiv2:oid "1.3.6.1.2.1.10.166.3.2.6.1.10";
        }
      }
    }

    container mplsTunnelARHopTable {
      description
       "The mplsTunnelARHopTable is used to indicate the
        hops for an MPLS tunnel defined in mplsTunnelTable,
        as reported by the MPLS signalling protocol. Thus at
        a transit LSR, this table (if the table is supported
        and if the signaling protocol is recording actual
        route information) contains the actual route of the
        whole tunnel. If the signaling protocol is not
        recording the actual route, this table MAY report
        the information from the mplsTunnelHopTable or the
        mplsTunnelCHopTable.
        
        Each row in this table is indexed by
        mplsTunnelARHopListIndex. Each row also has a
        secondary index mplsTunnelARHopIndex, corresponding
        to the next hop that this row corresponds to.
        
        Please note that since the information necessary to
        build entries within this table is not provided by
        some MPLS signalling protocols, implementation of
        this table is optional. Furthermore, since the
        information in this table is actually provided by
        the MPLS signalling protocol after the path has
        been set-up, the entries in this table are provided
        only for observation, and hence, all variables in
        this table are accessible exclusively as read-
        only.
        
        Note also that the contents of this table may change
        while it is being read because of re-routing
        activities. A network administrator may verify that
        the actual route read is consistent by reference to
        the mplsTunnelLastPathChange object.";
      smiv2:oid "1.3.6.1.2.1.10.166.3.2.7";

      list mplsTunnelARHopEntry {
        key "mplsTunnelARHopListIndex mplsTunnelARHopIndex";
        description
         "An entry in this table represents a tunnel hop.  An
          entry is created by the agent for signaled ERLSP
          set up by an MPLS signalling protocol.";
        smiv2:oid "1.3.6.1.2.1.10.166.3.2.7.1";

        leaf mplsTunnelARHopListIndex {
          type mpls-tc:MplsPathIndex;
          description
           "Primary index into this table identifying a
            particular recorded hop list.";
          smiv2:max-access "not-accessible";
          smiv2:oid "1.3.6.1.2.1.10.166.3.2.7.1.1";
        }

        leaf mplsTunnelARHopIndex {
          type mpls-tc:MplsPathIndex;
          description
           "Secondary index into this table identifying the
            particular hop.";
          smiv2:max-access "not-accessible";
          smiv2:oid "1.3.6.1.2.1.10.166.3.2.7.1.2";
        }

        leaf mplsTunnelARHopAddrType {
          type mpls-tc:TeHopAddressType;
          description
           "The Hop Address Type of this tunnel hop.
            
            Note that lspid(5) is a valid option only
            for tunnels signaled via CRLDP.";
          smiv2:defval "ipv4";
          smiv2:max-access "read-only";
          smiv2:oid "1.3.6.1.2.1.10.166.3.2.7.1.3";
        }

        leaf mplsTunnelARHopIpAddr {
          type mpls-tc:TeHopAddress;
          description
           "The Tunnel Hop Address for this tunnel hop.
            
            The type of this address is determined by the
            value of the corresponding mplsTunnelARHopAddrType.
            If mplsTunnelARHopAddrType is set to unnum(4),
             then this value contains the LSR Router ID of the
             unnumbered interface. Otherwise the agent SHOULD
             set this object to the zero-length string and the
             manager should ignore this object.";
          smiv2:defval "'00000000'H";
          smiv2:max-access "read-only";
          smiv2:oid "1.3.6.1.2.1.10.166.3.2.7.1.4";
        }

        leaf mplsTunnelARHopAddrUnnum {
          type mpls-tc:TeHopAddressUnnum;
          description
           "If mplsTunnelARHopAddrType is set to unnum(4), then
            this value will contain the interface identifier of
            the unnumbered interface for this hop. This object
            should be used in conjunction with
            mplsTunnelARHopIpAddr which would contain the LSR
            Router ID in this case. Otherwise the agent should
            set this object to zero-length string and the
            manager should ignore this.";
          smiv2:max-access "read-only";
          smiv2:oid "1.3.6.1.2.1.10.166.3.2.7.1.5";
        }

        leaf mplsTunnelARHopLspId {
          type mpls-tc:MplsLSPID;
          description
           "If mplsTunnelARHopAddrType is set to lspid(5), then
            this value will contain the LSP ID of this hop.
            This object is otherwise insignificant and should
            contain a value of 0 to indicate this fact.";
          smiv2:max-access "read-only";
          smiv2:oid "1.3.6.1.2.1.10.166.3.2.7.1.6";
        }
      }
    }

    container mplsTunnelCHopTable {
      description
       "The mplsTunnelCHopTable is used to indicate the
        hops, strict or loose, for an MPLS tunnel defined
        in mplsTunnelTable, as computed by a constraint-
        based routing protocol, based on the
        mplsTunnelHopTable for the outgoing direction of
        the tunnel. Thus at a transit LSR, this table (if
        the table is supported) MAY contain the path
        computed by the CSPF engine on (or on behalf of)
        this LSR. Each row in this table is indexed by
        mplsTunnelCHopListIndex.  Each row also has a
        secondary index mplsTunnelCHopIndex, corresponding
        to the next hop that this row corresponds to. In
        case we want to specify a particular interface on
        the originating LSR of an outgoing tunnel by which
        we want packets to exit the LSR, we specify this as
        the first hop for this tunnel in
        mplsTunnelCHopTable.
        
        Please note that since the information necessary to
        build entries within this table may not be
        supported by some LSRs, implementation of this
        table is optional. Furthermore, since the
        information in this table describes the path
        computed by the CSPF engine the entries in this
        table are read-only.";
      smiv2:oid "1.3.6.1.2.1.10.166.3.2.8";

      list mplsTunnelCHopEntry {
        key "mplsTunnelCHopListIndex mplsTunnelCHopIndex";
        description
         "An entry in this table represents a tunnel hop.  An
          entry in this table is created by a path
          computation engine using CSPF techniques applied to
          the information collected by routing protocols and
          the hops specified in the corresponding
          mplsTunnelHopTable.";
        smiv2:oid "1.3.6.1.2.1.10.166.3.2.8.1";

        leaf mplsTunnelCHopListIndex {
          type mpls-tc:MplsPathIndex;
          description
           "Primary index into this table identifying a
            particular computed hop list.";
          smiv2:max-access "not-accessible";
          smiv2:oid "1.3.6.1.2.1.10.166.3.2.8.1.1";
        }

        leaf mplsTunnelCHopIndex {
          type mpls-tc:MplsPathIndex;
          description
           "Secondary index into this table identifying the
            particular hop.";
          smiv2:max-access "not-accessible";
          smiv2:oid "1.3.6.1.2.1.10.166.3.2.8.1.2";
        }

        leaf mplsTunnelCHopAddrType {
          type mpls-tc:TeHopAddressType;
          description
           "The Hop Address Type of this tunnel hop.
            
            Note that lspid(5) is a valid option only
            for tunnels signaled via CRLDP.";
          smiv2:defval "ipv4";
          smiv2:max-access "read-only";
          smiv2:oid "1.3.6.1.2.1.10.166.3.2.8.1.3";
        }

        leaf mplsTunnelCHopIpAddr {
          type mpls-tc:TeHopAddress;
          description
           "The Tunnel Hop Address for this tunnel hop.
            The type of this address is determined by the
             value of the corresponding mplsTunnelCHopAddrType.
            
            If mplsTunnelCHopAddrType is set to unnum(4), then
             this value will contain the LSR Router ID of the
             unnumbered interface. Otherwise the agent should
             set this object to the zero-length string and the
             manager SHOULD ignore this object.";
          smiv2:defval "'00000000'H";
          smiv2:max-access "read-only";
          smiv2:oid "1.3.6.1.2.1.10.166.3.2.8.1.4";
        }

        leaf mplsTunnelCHopIpPrefixLen {
          type inet-address:InetAddressPrefixLength;
          description
           "If mplsTunnelCHopAddrType is set to ipv4(1) or
            ipv6(2), then this value will contain an
            appropriate prefix length for the IP address in
            object mplsTunnelCHopIpAddr. Otherwise this value
            is irrelevant and should be ignored.";
          smiv2:defval "32";
          smiv2:max-access "read-only";
          smiv2:oid "1.3.6.1.2.1.10.166.3.2.8.1.5";
        }

        leaf mplsTunnelCHopAsNumber {
          type mpls-tc:TeHopAddressAS;
          description
           "If mplsTunnelCHopAddrType is set to asnumber(3),
            then this value will contain the AS number of this
            hop. Otherwise the agent should set this object to
            zero-length string and the manager should ignore
            this.";
          smiv2:max-access "read-only";
          smiv2:oid "1.3.6.1.2.1.10.166.3.2.8.1.6";
        }

        leaf mplsTunnelCHopAddrUnnum {
          type mpls-tc:TeHopAddressUnnum;
          description
           "If mplsTunnelCHopAddrType is set to unnum(4), then
            this value will contain the unnumbered interface
            identifier of this hop. This object should be used
            in conjunction with mplsTunnelCHopIpAddr which
            would contain the LSR Router ID in this case.
            Otherwise the agent should set this object to zero-
            length string and the manager should ignore this.";
          smiv2:max-access "read-only";
          smiv2:oid "1.3.6.1.2.1.10.166.3.2.8.1.7";
        }

        leaf mplsTunnelCHopLspId {
          type mpls-tc:MplsLSPID;
          description
           "If mplsTunnelCHopAddrType is set to lspid(5), then
            this value will contain the LSP ID of this hop.
            This object is otherwise insignificant and should
            contain a value of 0 to indicate this fact.";
          smiv2:max-access "read-only";
          smiv2:oid "1.3.6.1.2.1.10.166.3.2.8.1.8";
        }

        leaf mplsTunnelCHopType {
          type enumeration {
            enum "strict" {
              value "1";
            }
            enum "loose" {
              value "2";
            }
          }
          description
           "Denotes whether this is tunnel hop is routed in a
            strict or loose fashion.";
          smiv2:max-access "read-only";
          smiv2:oid "1.3.6.1.2.1.10.166.3.2.8.1.9";
        }
      }
    }

    container mplsTunnelCRLDPResTable {
      description
       "The mplsTunnelCRLDPResTable allows a manager to
        specify which CR-LDP-specific resources are desired
        for an MPLS tunnel if that tunnel is signaled using
        CR-LDP. Note that these attributes are in addition
        to those specified in mplsTunnelResourceTable. This
        table also allows several tunnels to point to a
        single entry in this table, implying that these
        tunnels should share resources.";
      smiv2:oid "1.3.6.1.2.1.10.166.3.2.10";

      list mplsTunnelCRLDPResEntry {
        key "mplsTunnelResourceIndex";
        description
         "An entry in this table represents a set of resources
          for an MPLS tunnel established using CRLDP
          (mplsTunnelSignallingProto equal to crldp (3)). An
          entry can be created by a network administrator or
          by an SNMP agent as instructed by any MPLS
          signalling protocol.";
        smiv2:oid "1.3.6.1.2.1.10.166.3.2.10.1";

        leaf mplsTunnelResourceIndex {
          type leafref {
            path "/MPLS-TE-STD-MIB:MPLS-TE-STD-MIB/MPLS-TE-STD-MIB:mplsTunnelResourceTable/MPLS-TE-STD-MIB:mplsTunnelResourceEntry/MPLS-TE-STD-MIB:mplsTunnelResourceIndex";
          }
        }

        leaf mplsTunnelCRLDPResMeanBurstSize {
          type mpls-tc:MplsBurstSize;
          units "bytes";
          description
           "The mean burst size in bytes.";
          smiv2:max-access "read-write";
          smiv2:oid "1.3.6.1.2.1.10.166.3.2.10.1.1";
        }

        leaf mplsTunnelCRLDPResExBurstSize {
          type mpls-tc:MplsBurstSize;
          units "bytes";
          description
           "The Excess burst size in bytes.";
          reference
           "CR-LDP Specification, Section 4.3.";
          smiv2:max-access "read-write";
          smiv2:oid "1.3.6.1.2.1.10.166.3.2.10.1.2";
        }

        leaf mplsTunnelCRLDPResFrequency {
          type enumeration {
            enum "unspecified" {
              value "1";
            }
            enum "frequent" {
              value "2";
            }
            enum "veryFrequent" {
              value "3";
            }
          }
          description
           "The granularity of the availability of committed
            rate.";
          reference
           "CR-LDP Specification, Section 4.3.";
          smiv2:max-access "read-write";
          smiv2:oid "1.3.6.1.2.1.10.166.3.2.10.1.3";
        }

        leaf mplsTunnelCRLDPResWeight {
          type uint32 {
            range "0..255";
          }
          description
           "The relative weight for using excess bandwidth above
            its committed rate.  The value of 0 means that
            weight is not applicable for the CR-LSP.";
          reference
           "CR-LDP Specification, Section 4.3.";
          smiv2:defval "0";
          smiv2:max-access "read-write";
          smiv2:oid "1.3.6.1.2.1.10.166.3.2.10.1.4";
        }

        leaf mplsTunnelCRLDPResFlags {
          type uint32 {
            range "0..63";
          }
          description
           "The value of the 1 byte Flags conveyed as part of
            the traffic parameters during the establishment of
            the CRLSP. The bits in this object are to be
            interpreted as follows.
            
            +--+--+--+--+--+--+--+--+
            | Res |F6|F5|F4|F3|F2|F1|
            +--+--+--+--+--+--+--+--+
            
            Res - These bits are reserved. Zero on transmission.
            Ignored on receipt.
            F1 - Corresponds to the PDR.
            F2 - Corresponds to the PBS.
            F3 - Corresponds to the CDR.
            F4 - Corresponds to the CBS.
            F5 - Corresponds to the EBS.
            F6 - Corresponds to the Weight.
            
            Each flag if is a Negotiable Flag corresponding to a
            Traffic Parameter. The Negotiable Flag value zero
            denotes Not Negotiable and value one denotes
            Negotiable.";
          reference
           "1. Section 4.3, Constraint-Based LSP Setup using
            LDP, Jamoussi (Editor), RFC 3212, January 2002";
          smiv2:defval "0";
          smiv2:max-access "read-write";
          smiv2:oid "1.3.6.1.2.1.10.166.3.2.10.1.5";
        }

        leaf mplsTunnelCRLDPResRowStatus {
          type snmpv2-tc:RowStatus;
          description
           "This variable is used to create, modify, and/or
            delete a row in this table.  When a row in this
            table is in active(1) state, no objects in that row
            can be modified by the agent except
            mplsTunnelCRLDPResRowStatus and
            mplsTunnelCRLDPResStorageType.";
          smiv2:max-access "read-write";
          smiv2:oid "1.3.6.1.2.1.10.166.3.2.10.1.6";
        }

        leaf mplsTunnelCRLDPResStorageType {
          type snmpv2-tc:StorageType;
          description
           "The storage type for this CR-LDP Resource entry.
            Conceptual rows having the value 'permanent'
            need not allow write-access to any columnar
            objects in the row.";
          smiv2:defval "volatile";
          smiv2:max-access "read-write";
          smiv2:oid "1.3.6.1.2.1.10.166.3.2.10.1.7";
        }
      }
    }
  }

  smiv2:alias "mplsTunnelPerfTable" {
    description
     "This table provides per-tunnel instance MPLS
      performance information.";
    smiv2:oid "1.3.6.1.2.1.10.166.3.2.9";
  }

  smiv2:alias "mplsTunnelPerfEntry" {
    description
     "An entry in this table is created by the LSR for
      every tunnel.  Its is an extension to
      mplsTunnelEntry.";
    smiv2:oid "1.3.6.1.2.1.10.166.3.2.9.1";
  }

  augment "/MPLS-TE-STD-MIB:MPLS-TE-STD-MIB/MPLS-TE-STD-MIB:mplsTunnelTable/MPLS-TE-STD-MIB:mplsTunnelEntry" {
    description
     "An entry in this table is created by the LSR for
      every tunnel.  Its is an extension to
      mplsTunnelEntry.";
    smiv2:oid "1.3.6.1.2.1.10.166.3.2.9.1";

    leaf mplsTunnelPerfPackets {
      type yang:counter32;
      description
       "Number of packets forwarded by the tunnel.
        This object should represents the 32-bit
        value of the least significant part of the
        64-bit value if both mplsTunnelPerfHCPackets
        is returned.";
      smiv2:max-access "read-only";
      smiv2:oid "1.3.6.1.2.1.10.166.3.2.9.1.1";
    }

    leaf mplsTunnelPerfHCPackets {
      type yang:counter64;
      description
       "High capacity counter for number of packets
        forwarded by the tunnel. ";
      smiv2:max-access "read-only";
      smiv2:oid "1.3.6.1.2.1.10.166.3.2.9.1.2";
    }

    leaf mplsTunnelPerfErrors {
      type yang:counter32;
      description
       "Number of packets dropped because of errors or for
        other reasons.";
      smiv2:max-access "read-only";
      smiv2:oid "1.3.6.1.2.1.10.166.3.2.9.1.3";
    }

    leaf mplsTunnelPerfBytes {
      type yang:counter32;
      description
       "Number of bytes forwarded by the tunnel.
        This object should represents the 32-bit
        value of the least significant part of the
        64-bit value if both mplsTunnelPerfHCBytes
        is returned.";
      smiv2:max-access "read-only";
      smiv2:oid "1.3.6.1.2.1.10.166.3.2.9.1.4";
    }

    leaf mplsTunnelPerfHCBytes {
      type yang:counter64;
      description
       "High capacity counter for number of bytes forwarded
        by the tunnel.";
      smiv2:max-access "read-only";
      smiv2:oid "1.3.6.1.2.1.10.166.3.2.9.1.5";
    }
  }

  notification mplsTunnelUp {
    description
     "This notification is generated when a
      mplsTunnelOperStatus object for one of the
      configured tunnels is about to leave the down state
      and transition into some other state (but not into
      the notPresent state).  This other state is
      indicated by the included value of
      mplsTunnelOperStatus.";
    smiv2:oid "1.3.6.1.2.1.10.166.3.0.1";

    container object-1 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelAdminStatus {
        type leafref {
          path "/MPLS-TE-STD-MIB:MPLS-TE-STD-MIB/MPLS-TE-STD-MIB:mplsTunnelTable/MPLS-TE-STD-MIB:mplsTunnelEntry/MPLS-TE-STD-MIB:mplsTunnelAdminStatus";
        }
      }
    }

    container object-2 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelOperStatus {
        type leafref {
          path "/MPLS-TE-STD-MIB:MPLS-TE-STD-MIB/MPLS-TE-STD-MIB:mplsTunnelTable/MPLS-TE-STD-MIB:mplsTunnelEntry/MPLS-TE-STD-MIB:mplsTunnelOperStatus";
        }
      }
    }
  }

  notification mplsTunnelDown {
    description
     "This notification is generated when a
      mplsTunnelOperStatus object for one of the
      configured tunnels is about to enter the down state
      from some other state (but not from the notPresent
      state).  This other state is indicated by the
      included value of mplsTunnelOperStatus.";
    smiv2:oid "1.3.6.1.2.1.10.166.3.0.2";

    container object-1 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelAdminStatus {
        type leafref {
          path "/MPLS-TE-STD-MIB:MPLS-TE-STD-MIB/MPLS-TE-STD-MIB:mplsTunnelTable/MPLS-TE-STD-MIB:mplsTunnelEntry/MPLS-TE-STD-MIB:mplsTunnelAdminStatus";
        }
      }
    }

    container object-2 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelOperStatus {
        type leafref {
          path "/MPLS-TE-STD-MIB:MPLS-TE-STD-MIB/MPLS-TE-STD-MIB:mplsTunnelTable/MPLS-TE-STD-MIB:mplsTunnelEntry/MPLS-TE-STD-MIB:mplsTunnelOperStatus";
        }
      }
    }
  }

  notification mplsTunnelRerouted {
    description
     "This notification is generated when a tunnel is
      rerouted. If the mplsTunnelARHopTable is used, then
      this tunnel instance's entry in the
      mplsTunnelARHopTable MAY contain the new path for
      this tunnel some time after this trap is issued by
      the agent.";
    smiv2:oid "1.3.6.1.2.1.10.166.3.0.3";

    container object-1 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelAdminStatus {
        type leafref {
          path "/MPLS-TE-STD-MIB:MPLS-TE-STD-MIB/MPLS-TE-STD-MIB:mplsTunnelTable/MPLS-TE-STD-MIB:mplsTunnelEntry/MPLS-TE-STD-MIB:mplsTunnelAdminStatus";
        }
      }
    }

    container object-2 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelOperStatus {
        type leafref {
          path "/MPLS-TE-STD-MIB:MPLS-TE-STD-MIB/MPLS-TE-STD-MIB:mplsTunnelTable/MPLS-TE-STD-MIB:mplsTunnelEntry/MPLS-TE-STD-MIB:mplsTunnelOperStatus";
        }
      }
    }
  }

  notification mplsTunnelReoptimized {
    description
     "This notification is generated when a tunnel is
      reoptimized. If the mplsTunnelARHopTable is used,
      then this tunnel instance's entry in the
      mplsTunnelARHopTable MAY contain the new path for
      this tunnel some time after this trap is issued by
      the agent.";
    smiv2:oid "1.3.6.1.2.1.10.166.3.0.4";

    container object-1 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelAdminStatus {
        type leafref {
          path "/MPLS-TE-STD-MIB:MPLS-TE-STD-MIB/MPLS-TE-STD-MIB:mplsTunnelTable/MPLS-TE-STD-MIB:mplsTunnelEntry/MPLS-TE-STD-MIB:mplsTunnelAdminStatus";
        }
      }
    }

    container object-2 {

      leaf mplsTunnelIndex {
        type leafref {
          path "/MPLS-TE-STD-MIB:MPLS-TE-STD-MIB/MPLS-TE-STD-MIB:mplsTunnelTable/MPLS-TE-STD-MIB:mplsTunnelEntry/MPLS-TE-STD-MIB:mplsTunnelIndex";
        }
      }

      leaf mplsTunnelInstance {
        type leafref {
          path "/MPLS-TE-STD-MIB:MPLS-TE-STD-MIB/MPLS-TE-STD-MIB:mplsTunnelTable/MPLS-TE-STD-MIB:mplsTunnelEntry/MPLS-TE-STD-MIB:mplsTunnelInstance";
        }
      }

      leaf mplsTunnelIngressLSRId {
        type leafref {
          path "/MPLS-TE-STD-MIB:MPLS-TE-STD-MIB/MPLS-TE-STD-MIB:mplsTunnelTable/MPLS-TE-STD-MIB:mplsTunnelEntry/MPLS-TE-STD-MIB:mplsTunnelIngressLSRId";
        }
      }

      leaf mplsTunnelEgressLSRId {
        type leafref {
          path "/MPLS-TE-STD-MIB:MPLS-TE-STD-MIB/MPLS-TE-STD-MIB:mplsTunnelTable/MPLS-TE-STD-MIB:mplsTunnelEntry/MPLS-TE-STD-MIB:mplsTunnelEgressLSRId";
        }
      }

      leaf mplsTunnelOperStatus {
        type leafref {
          path "/MPLS-TE-STD-MIB:MPLS-TE-STD-MIB/MPLS-TE-STD-MIB:mplsTunnelTable/MPLS-TE-STD-MIB:mplsTunnelEntry/MPLS-TE-STD-MIB:mplsTunnelOperStatus";
        }
      }
    }
  }

  smiv2:alias "mplsTeStdMIB" {
    smiv2:oid "1.3.6.1.2.1.10.166.3";
  }

  smiv2:alias "mplsTeNotifications" {
    smiv2:oid "1.3.6.1.2.1.10.166.3.0";
  }

  smiv2:alias "mplsTeScalars" {
    smiv2:oid "1.3.6.1.2.1.10.166.3.1";
  }

  smiv2:alias "mplsTeObjects" {
    smiv2:oid "1.3.6.1.2.1.10.166.3.2";
  }

  smiv2:alias "mplsTeConformance" {
    smiv2:oid "1.3.6.1.2.1.10.166.3.3";
  }

  smiv2:alias "mplsTeGroups" {
    smiv2:oid "1.3.6.1.2.1.10.166.3.3.1";
  }

  smiv2:alias "mplsTeCompliances" {
    smiv2:oid "1.3.6.1.2.1.10.166.3.3.2";
  }

}
