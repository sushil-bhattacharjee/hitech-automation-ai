submodule Cisco-IOS-XE-ip {
  belongs-to Cisco-IOS-XE-native {
    prefix ios;
  }

  import cisco-semver {
    prefix cisco-semver;
  }
  import ietf-inet-types {
    prefix inet;
  }
  import Cisco-IOS-XE-types {
    prefix ios-types;
  }
  import Cisco-IOS-XE-interface-common {
    prefix ios-ifc;
  }
  import Cisco-IOS-XE-features {
    prefix ios-features;
  }
  include Cisco-IOS-XE-interfaces;

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native IP Yang Model.
     Copyright (c) 2016-2021 by Cisco Systems, Inc.
     All rights reserved.";

  revision 2021-07-10 {
    description
      "- Added container vxlan for Tenant Routed Multicast Data MDT support";
    cisco-semver:module-version "7.0.17060(m)";
  }
  revision 2021-07-01 {
    description
      "- Added ip ssh bulk-mode support
       - Fixed configuration roll-back ordering for ip prefix-lists in controller mode
       - Added new allow-evpn leaf
       - Added support to include interface module for fixing yang errors
       - Changed 'ip ssh source-interface' from leaf to container
       - Fixed the must constraints of mdt model";
    cisco-semver:module-version "7.0.0";
  }
  revision 2021-03-01 {
    description
      "- Modified range for  vrf maximum-routes
       - Added maximum-routes support for ipv6 address-family under vrf";
    cisco-semver:module-version "6.0.0";
  }
  revision 2020-11-01 {
    description
      "- Merge prefix-list model from cloned model";
    cisco-semver:module-version "5.0.0";
  }
  revision 2020-07-01 {
    description
      "NEEDS TO BE FIXED
       - Add flatten-container for track-id-name
       - Deprecated 'ip ftp passive' node and created
         a new node 'passive-enable'
       - Added support for IP route track name'
       - Added support for 'ip route segment-routing'
       - Added support for 'mdt auto-discovery pim inter-as'
       - Added fixes for route-replicate
       - Added support for 'mdt auto-discovery interworking vxlan-pim'
       - Fixed the maximum username entries for 'ip ssh pub-key-chain username'
       - added new list for track";
    cisco-semver:module-version "4.0.0";
  }
  revision 2020-03-01 {
    description
      "- Added support for 'ip domain lookup recursive'
       - Added support for 'ip domain lookup vrf <vrf-name> source-interface
         <interface-name>'
       - Added prefix-lists cli-remove-before-change for replace
       - Added default value for metric in ip route interface forwarding list metric
       - Updated route-target configuration
       - Added support for 'ip tcp mss' command
       - Added support for 'route-replicate' command
       - Extend address-family import and export configuration";
    cisco-semver:module-version "3.0.0";
  }
  revision 2019-11-01 {
    description
      "
       - Changed IP routing from a presence container to a leaf for dependant
       routing protocols to check before committing changes
       - Address arp model gaps;
       - Added dependency on ip route over the interface";
    cisco-semver:module-version "2.0.0";
  }
  revision 2019-07-01 {
    description
      "- Establish semantic version baseline
       - Updated mdt data to have a container for default scope and a list
         for all user scope
       - Added support for 'ip domain periodic-resolve <val>'
       - Added support for ip ssh dh min size
       - Added support for ip local policy route-map
       - Address MVPN mdt model gaps";
    cisco-semver:module-version "1.0.0";
  }
  revision 2019-02-04 {
    description
      "Fixed a bug in ip prefix-list";
  }
  revision 2019-01-29 {
    description
      "vManage cannot handle choice for VRF ip name-server";
  }
  revision 2019-01-27 {
    description
      "Deprecating ip domain-lookup and fixing a bug in the model";
  }
  revision 2019-01-09 {
    description
      "Backward compatibility for multiple name-servers in VRF";
  }
  revision 2019-01-04 {
    description
      "Allow multiple name-servers in VRF";
  }
  revision 2018-11-28 {
    description
      "added missing | in pattern string of ip prefix-list name leaf";
  }
  revision 2018-11-07 {
    description
      "Cleanup spelling errors in description statements";
  }
  revision 2018-10-13 {
    description
      "added model for ip route vrf topology and ip route topology";
  }
  revision 2018-10-08 {
    description
      "Make dhcp option available to 'ip route' following outgoing interface";
  }
  revision 2018-09-26 {
    description
      "Add cli-disallow-value 'dhcp|DHCP' to 'ip route' for non-dhcp configurations";
  }
  revision 2018-09-19 {
    description
      "added model for ip route static bfd *";
  }
  revision 2018-09-18 {
    description
      "Remove full-command annotation from VRF definition";
  }
  revision 2018-09-07 {
    description
      "Add must constraint to ip route vrf, on vrf & address-family";
  }
  revision 2018-09-06 {
    description
      "Added support to all option under 'ip route static install-routes-recurse-via-nexthop'";
  }
  revision 2018-09-03 {
    description
      "removed deprecated CLI 'ip domain-name' model";
  }
  revision 2018-08-20 {
    description
      "add more support to vrf definition";
  }
  revision 2018-08-03 {
    description
      "Corrected ip prefix-list model to make one entry with one representation with seq";
  }
  revision 2018-07-11 {
    description
      "add support to vrf definition rd to use rd asn dot notation";
  }
  revision 2018-05-24 {
    description
      "add support to get default for ip domain lookup";
  }
  revision 2018-05-09 {
    description
      "stitching leaf moved to the vrf group";
  }
  revision 2018-05-03 {
    description
      "stitching leaf added in vrf definition";
  }
  revision 2018-04-18 {
    description
      "add max limit for ip name-server";
  }
  revision 2018-04-04 {
    description
      "add tailf:cli-remove-before-change for vrf definition rd";
  }
  revision 2018-03-12 {
    description
      "Add dependency to 'export map' on rd, in order to match CLI behavior";
  }
  revision 2018-02-09 {
    description
      "fix ip prefix-list deleting issue";
  }
  revision 2018-02-02 {
    description
      "Change ip domain to leaf-list to match IOS behavior";
  }
  revision 2018-01-11 {
    description
      "Support ip host and ip host vrf replacement";
  }
  revision 2017-10-25 {
    description
      "Support ip host and ip host vrf with multiple ipv4/ipv6 address";
  }
  revision 2017-08-28 {
    description
      "Extend modeling for multicast";
  }
  revision 2017-07-24 {
    description
      "Add ip ssh server peruser session limit";
  }
  revision 2017-06-29 {
    description
      "This revision fixes the compiling warning in ip route";
  }
  revision 2017-06-27 {
    description
      "Add maxstartups to ssh-server";
  }
  revision 2017-05-17 {
    description
      "This revision fixes the problem in ip route";
  }
  revision 2017-04-10 {
    description
      "This revision fixes the problem where CDB not updated when configuring
       through CLI for ip routing protocol purge interface";
  }
  revision 2017-03-14 {
    description
      "This revision fixes the problem where interface Loopback joining with
       its name in display";
  }
  revision 2017-03-02 {
    description
      "This revision enhances NED model for IWAN 3.0.2 Ph 1 - Misc Config:
       - adds config-ip-ssh-algorithm-grouping grouping.
       - adds vrf list node under host node";
  }
  revision 2017-02-23 {
    description
      "This revision adds support for IP explicit-path";
  }
  revision 2017-02-07 {
    description
      "Initial revision";
  }

  typedef rd-type {
    type string {
      pattern '(\d*(.\d*)*)?:(\d*(.\d*)*)?';
    }
  }

  typedef mdt-data-list-type {
    type union {
      type uint16 {
        range "100..199";
      }
      type uint16 {
        range "2000..2699";
      }
      type string {
        pattern '[a-fA-F].*';
      }
    }
  }

  typedef vpn-id-type {
    type string {
      pattern '[0-9a-fA-F][0-9a-fA-F]?[0-9a-fA-F]?:[0-9a-fA-F][0-9a-fA-F]?[0-9a-fA-F]?[0-9a-fA-F]?';
    }
  }

  grouping route-map-group {
    leaf route-map {
      description
        "Route map reference";
      type string;
    }
  }

  grouping src-protocol-grouping {
    container source-proto-config {
      container all {
        description
          "All routes";
        presence "true";
        uses route-map-group;
      }
      container mobile {
        when 'not(../all)';
        description
          "Mobile routes";
        presence "true";
        uses route-map-group;
      }
      container static {
        when 'not(../all)';
        description
          "Static routes";
        presence "true";
        uses route-map-group;
      }
      container connected {
        when 'not(../all)';
        description
          "Connected Routes";
        presence "true";
        uses route-map-group;
      }
      container rip {
        when 'not(../all)';
        description
          "Routing Information Protocol (RIP)";
        presence "true";
        uses route-map-group;
      }
      container odr {
        when 'not(../all)';
        description
          "on demand stub routes";
        presence "true";
        uses route-map-group;
      }
      list bgp {
        description
          "Border Gateway Protocol (BGP)";
        when 'not(../all)';
        key "asn";
        leaf asn {
          type ios-types:bgp-as-number-type;
        }
        uses route-map-group;
      }
      list eigrp {
        description
          "Enhanced Interior Gateway Routing Protocol (EIGRP)";
        when 'not(../all)';
        key "asn";
        leaf asn {
          type uint32 {
            range "1..65535";
          }
        }
        uses route-map-group;
      }
      container isis {
        when 'not(../all)';
        description
          "ISO IS-IS";
        presence "true";
        uses route-map-group;
      }
      container isisareatag {
        when 'not(../all)';
        description
          "ISIS with area tag";
        list isis {
          when 'not(../../all)';
          description
            "ISO IS-IS";
          key "area-tag";
          leaf area-tag {
            type string;
          }
          uses route-map-group;
        }
      }
      list ospf {
        when 'not(../all)';
        description
          "Open Shortest Path  First (OSPF)";
        key "process-id";
        leaf process-id {
          description
            "list ospf process";
          type uint32 {
            range "1..65535";
          }
        }
        uses route-map-group;
      }
    }
  }

  grouping route-replicate-grouping {
    container route-replicate {
      description
        "Replicate (import) routes from another topology and vrf";
      container from {
        description
          "from";
        list vrf {
          must "unicast/source-proto-config/all or
                unicast/source-proto-config/static or
                unicast/source-proto-config/connected or
                unicast/source-proto-config/mobile or
                unicast/source-proto-config/rip or
                unicast/source-proto-config/odr or
                unicast/source-proto-config/bgp or
                unicast/source-proto-config/isis or
                unicast/source-proto-config/isisareatag/isis or
                unicast/source-proto-config/ospf or
                unicast/source-proto-config/eigrp" {
            error-message "protocol config cannot be empty! (if deletion, delete the list vrf)";
          }
          key "name";
          leaf name {
            type string {
              pattern '([^g].*)|(g[^l].*)|(gl[^o].*)(glo[^b])|(glob[^a].*)|(globa..*)' {
                error-message "substrings of 'global' are reserved.Please use 'global' instead!";
              }
            }
          }
          container unicast {
            description
              "unicast";
            uses src-protocol-grouping;
          }
        }
      }
      container recursion-policy {
        description
          "recursion policy";
        leaf destination {
          description
            "recursion policy ";
          type empty;
        }
      }
    }
  }

  grouping vrf-default-route-target-grouping {
    choice export-choice {
      leaf export {
        type empty;
      }
      container export-asn {
        list export {
          description
            "Export Target-VPN community";
          key "asn-ip";
          leaf asn-ip {
            type ios-types:asn-ip-type;
          }
        }
      }
    }
    choice import-choice {
      leaf import {
        type empty;
      }
      container import-asn {
        list import {
          description
            "Import Target-VPN community";
          key "asn-ip";
          leaf asn-ip {
            type ios-types:asn-ip-type;
          }
        }
      }
    }
  }

  grouping vrf-af-route-target-grouping {
    container export-route-target {
      list without-stitching {
        description
          "Export Target-VPN community";
        key "asn-ip";
        leaf asn-ip {
          type ios-types:asn-ip-type;
        }
      }
      list with-stitching {
        description
          "Export Target-VPN community";
        key "asn-ip";
        leaf asn-ip {
          type ios-types:asn-ip-type;
        }
        leaf stitching {
          description
            "VXLAN route target set";
          mandatory true;
          type empty;
        }
      }
    }
    container import-route-target {
      list without-stitching {
        description
          "Import Target-VPN community";
        key "asn-ip";
        leaf asn-ip {
          type ios-types:asn-ip-type;
        }
      }
      list with-stitching {
        description
          "Import Target-VPN community";
        key "asn-ip";
        leaf asn-ip {
          type ios-types:asn-ip-type;
        }
        leaf stitching {
          description
            "VXLAN route target set";
          mandatory true;
          type empty;
        }
      }
    }
    list export {
      status obsolete;
      description
        "Export Target-VPN community (OBSOLETE)";
      key "asn-ip";
      leaf asn-ip {
        status obsolete;
        type ios-types:asn-ip-type;
      }
      leaf stitching {
        status obsolete;
        description
          "VXLAN route target set (OBSOLETE)";
        type empty;
      }
    }
    list import {
      status obsolete;
      description
        "Import Target-VPN community (OBSOLETE)";
      key "asn-ip";
      leaf asn-ip {
        status obsolete;
        type ios-types:asn-ip-type;
      }
      leaf stitching {
        status obsolete;
        description
          "VXLAN route target set (OBSOLETE)";
        type empty;
      }
    }
  }

  grouping vrf-route-target-grouping {
    list export {
      description
        "Export Target-VPN community";
      key "asn-ip";
      leaf asn-ip {
        type ios-types:asn-ip-type;
      }
      leaf stitching {
        description
          "VXLAN route target set";
        type empty;
      }
    }
    list import {
      description
        "Import Target-VPN community";
      key "asn-ip";
      leaf asn-ip {
        type ios-types:asn-ip-type;
      }
      leaf stitching {
        description
          "VXLAN route target set";
        type empty;
      }
    }
  }

  grouping vrf-maximum-grouping {
    container maximum {
      description
        "Maximum number of routes allowed in this routing table";
      must 'routes' {
        error-message "Max Routes value  must always be configured";
      }
      presence "Maximum number of routes allowed in this routing table";
      leaf routes {
        description
          "Maximum number of routes allowed in this routing table";
        type uint32 {
          range "1..4294967294";
        }
      }
      choice maximum-choice {
        mandatory true;
        case threshold-case {
          leaf threshold {
            description
              "Threshold";
            type uint16 {
              range "1..100";
            }
          }
          leaf reinstall {
            description
              "Reinstall previous rejected route due to over maximum route limit";
            type uint16 {
              range "1..100";
            }
          }
        }
        case warning-case {
          leaf warning-only {
            description
              "Only give a warning message if is limit exceeded";
            type empty;
          }
        }
      }
    }
  }

  grouping vrf-loopback-grouping {
    leaf Loopback {
      description
        "Loopback interface number";
      type uint32 {
        range "0..2147483647";
      }
    }
  }

  grouping config-global-address-family {
    container global-address-family {
      description
        " Enter address-family base routing topology mode";
      container ipv4 {
        description
          "Address family IPv4";
        presence "true";
        uses route-replicate-grouping;
      }
    }
  }

  grouping conf-vrf-definition-default-grouping {
    leaf description {
      description
        "VRF specific description";
      type empty;
    }
    container ipv4 {
      description
        "VRF IPv4 configuration";
      container multicast {
        description
          "IP multicast configuration";
        leaf multitopology {
          description
            "Enable Multicast-Specific RPF Topology";
          type empty;
        }
      }
    }
    container ipv6 {
      description
        "VRF IPv6 configuration";
      container multicast {
        description
          "IP multicast configuration";
        leaf multitopology {
          description
            "Enable Multicast-Specific RPF Topology";
          type empty;
        }
      }
    }
    leaf rd {
      description
        "Specify Route Distinguisher";
      type union {
        type string {
          pattern '[0-9]+:[0-9]+';
        }
        type inet:ipv4-address;
        type ios-types:asn-ip-type;
      }
    }
    container address-family {
      description
        "Enter Address Family command mode";
      container ipv4 {
        description
          "Address family";
        presence "true";
        choice modifier {
          leaf unicast {
            type empty;
          }
          leaf multicast {
            type empty;
          }
        }
      }
      container ipv6 {
        description
          "Address family";
        presence "true";
        choice modifier {
          leaf unicast {
            type empty;
          }
          leaf multicast {
            type empty;
          }
        }
      }
    }
    container route-target {
      description
        "Specify Target VPN Extended Communities";
      choice def-route-target {
        case emtpy-rt-case {
          leaf empty-rt {
            type empty;
          }
        }
        case default-rt {
          uses vrf-default-route-target-grouping;
        }
      }
    }
    container vnet {
      description
        "Virtual NETworking configuration";
      leaf tag {
        description
          "use default tag";
        type empty;
      }
    }
    container vpn {
      description
        "Configure VPN ID as specified in rfc2685";
      leaf id {
        description
          "use default VPN ID";
        type empty;
      }
    }
  }

  grouping config-mvpn-mdt-grouping {
    container mdt {
      description
        "Backbone Multicast Distribution Tree";
      container default {
        description
          "The default group";
        leaf address {
          type inet:ipv4-address;
        }
        leaf ingress-replication {
          description
            "Use Ingress-Replication for the default MDT";
          type empty;
        }
        container mpls {
          description
            "MPLS tunnel options";
          container mldp-config {
            description
              "Use a MLDP LSP to create the default MDT";
            leaf-list mp2mp-root-address {
              description
                "MP2MP LSP root address";
              type inet:ipv4-address;
              must 'not (../p2mp)' {
                error-message
                  "%MVPN: Please unconfigure MLDP Rosen P2MP
                   Profile in this address-family";
              }
            }
            leaf p2mp {
              description
                "Use a P2MP MLDP LSP to create the default MDT";
              type empty;
              must 'not (../mp2mp-root-address)' {
                error-message
                  "%MVPN: Please unconfigure MLDP Rosen MP2MP
                   Profile in this address-family";
              }
            }
          }
          leaf mldp {
            description
              "OBSOLETE : Use 'mldp-config' under 'mpls' container";
            status obsolete;
            type inet:ipv4-address;
          }
        }
        leaf vxlan {
          description
            "Vxlan options for default MDT. Specify multicast group address.";
          type inet:ipv4-address;
        }
      }
      container auto-discovery {
        description
          "BGP auto-discovery for MVPN";
        choice auto-discovery {
          case pim-options {
            container pim-options {
              description
                "BGP auto-discovery for PIM";
              leaf pim {
                description
                  "BGP auto-discovery for PIM";
                type empty;
                mandatory true;
              }
              leaf inter-as {
                description
                  "Enable Inter-AS BGP auto-discovery";
                type empty;
              }
              leaf pim-tlv-announce {
                description
                  "Announce PIM TLV for data MDT";
                type empty;
              }
              leaf mdt-hello-enable {
                description
                  "Enable PIM Hellos over MDT interface";
                type empty;
              }
            }
          }
          case ingress-replication {
            container ingress-replication {
              description
                "BGP auto-discovery for Ingress-Replication";
              leaf ingress-replication {
                description
                  "BGP auto-discovery for Ingress-Replication";
                type empty;
                mandatory true;
              }
              leaf inter-as {
                description
                  "Enable Inter-AS BGP auto-discovery";
                type empty;
              }
              leaf mdt-hello-enable {
                description
                  "Enable PIM Hellos over MDT interface";
                type empty;
              }
            }
          }
          case mldp {
            container mldp {
              description
                "BGP auto-discovery for MLDP";
              leaf mldp {
                description
                  "BGP auto-discovery for MLDP";
                type empty;
                mandatory true;
              }
              leaf inter-as {
                description
                  "Enable Inter-AS BGP auto-discovery";
                type empty;
              }
              leaf pim-tlv-announce {
                description
                  "Announce PIM TLV for data MDT";
                type empty;
              }
              leaf mdt-hello-enable {
                description
                  "Enable PIM Hellos over MDT interface";
                type empty;
              }
            }
          }
          case vxlan {
            container vxlan-config {
              description
                "BGP auto-discovery for VxLAN";
              leaf vxlan {
                description
                  "BGP auto-discovery for VxLAN";
                type empty;
                mandatory true;
              }
              leaf inter-as {
                description
                  "Enable Inter-AS BGP auto-discovery";
                type empty;
              }
            }
          }
          case interworking {
            container interworking {
              choice interworking {
                case vxlan-pim {
                  container vxlan-pim-config {
                    description
                      "BGP auto-discovery for VxLAN PIM interworking";
                    leaf vxlan-pim {
                      description
                        "BGP auto-discovery for VxLAN PIM";
                      type empty;
                      mandatory true;
                    }
                    leaf inter-as {
                      description
                        "Enable Inter-AS BGP auto-discovery";
                      type empty;
                    }
                  }
                }
              }
            }
          }
        }
        leaf receiver-site {
          description
            "BGP receiver only site for MVPN";
          type empty;
        }
        leaf pim {
          description
            "BGP auto-discovery for PIM";
          type empty;
          status deprecated;
        }
      }
      container data {
        description
          "MDT data trees";
        list multicast {
          key "address wildcard";
          leaf address {
            type inet:ipv4-address;
          }
          leaf wildcard {
            type inet:ipv4-address;
          }
          leaf list {
            description
              "Access-list";
            type ios-types:ext-acl-type;
          }
        }
        leaf list {
          description
            "Access-list";
          type ios-types:ext-acl-type;
        }
        leaf threshold {
          description
            "MDT switching threshold";
          type uint32 {
            range "1..4294967";
          }
        }
        container mpls {
          description
            "MPLS tunnel options";
          container mldp {
            description
              "Use a MLDP LSP to create the data MDT";
            container default-scope {
              leaf mdt-instances {
                description
                  "Number of data MDT instances under default-scope";
                type uint16 {
                  range "1..5000";
                }
              }
              leaf list {
                description
                  "Access-list";
                type ios-types:ext-acl-type;
              }
              leaf immediate-switch {
                description
                  "Switch immediately to Data MDT tree";
                type empty;
              }
            }
            list user-defined-scope {
              description
                "Use a MLDP LSP to create the data MDT. This is a list for
                 user-defined scopes";
              key "scope";
              leaf mdt-instances {
                description
                  "Number of data MDT instances under user-defined scope";
                type uint16 {
                  range "1..5000";
                }
              }
              leaf list {
                description
                  "Access-list";
                type ios-types:ext-acl-type;
              }
              leaf scope {
                description
                  "Scope of Data MDT";
                type uint8 {
                  range "1..255";
                }
              }
              leaf immediate-switch {
                description
                  "Switch immediately to Data MDT tree";
                type empty;
              }
            }
          }
        }
        container ingress-replication {
          description
            "Use Ingress-Replication to create the data MDT";
          presence "true";
          leaf mdt-instances {
            description
              "Number of data MDT instances";
            type uint16 {
              range "1..20000";
            }
          }
          leaf list {
            description
              "Access-list";
            type ios-types:ext-acl-type;
          }
          leaf immediate-switch {
            description
              "Switch immediately to Data MDT tree";
            type empty;
          }
        }
        container vxlan {
          description
            "Use vxlan to create data MDT";
          list multicast {
            key "address wildcard";
            leaf address {
              type inet:ipv4-address;
            }
            leaf wildcard {
              type inet:ipv4-address;
            }
            leaf list {
              description
                "Access-list";
              type ios-types:ext-acl-type;
            }
          }
        }
      }
      leaf direct {
        description
          "Direct MDT";
        type empty;
      }
      leaf log-reuse {
        description
          "Event logging for data MDT reuse";
        type empty;
      }
      leaf mtu {
        description
          "The MTU";
        type uint16 {
          range "576..18010";
        }
      }
      container overlay {
        description
          "MDT Overlay Protocol";
        container use-bgp-config {
          description
            "BGP options for Overlay Signaling";
          presence "true";
          leaf spt-only {
            description
              "Enable Shortest path tree -only ASM mode";
            type empty;
          }
        }
        leaf use-bgp {
          description
            "DEPRECATED: Use 'use-bgp-config' under 'overlay' container";
          status deprecated;
          type empty;
        }
        container bgp {
          description
            "BGP Overlay signalling";
          leaf shared-tree-prune-delay {
            description
              "Delay before shared tree is pruned at C-RP PE";
            type uint16 {
              range "1..1800";
            }
            default "60";
          }
          leaf source-tree-prune-delay {
            description
              "Delay before source tree is pruned at C-S PE";
            type uint16 {
              range "0..300";
            }
            default "30";
          }
        }
      }
      container partitioned {
        description
          "Partitioned Multicast Distribution Tree";
        leaf ingress-replication {
          description
            "Use Ingress-Replication for the partitioned MDT";
          type empty;
        }
        leaf mldp {
          description
            "Use MLDP to create the partitioned MDT";
          type enumeration {
            enum p2mp;
            enum mp2mp;
          }
        }
      }
      leaf mdt-preference {
        description
          "MDT preference (default pim mldp)";
        type enumeration {
          enum mldp;
          enum pim;
        }
        default "pim";
      }
      leaf-list preference {
        description
          "obsolete MDT preference (default pim mldp)";
        status obsolete;
        type enumeration {
          enum mldp;
          enum pim;
        }
      }
      container strict-rpf {
        description
          "Enable strict RPF check";
        leaf interface {
          description
            "Interface based strict RPF check";
          type empty;
        }
      }
    }
  }

  grouping config-vrf-definition-grouping {
    container vrf {
      description
        "VRF commands";
      list definition {
        description
          "VRF definition mode";
        key "name";
        leaf name {
          description
            "WORD;;VRF name";
          type string;
        }
        container default {
          uses conf-vrf-definition-default-grouping;
        }
        leaf description {
          description
            "VRF specific description";
          type string {
            length "1..244";
          }
        }
        container ipv4 {
          description
            "VRF IPv4 configuration";
          container multicast {
            description
              "IP multicast configuration";
            leaf multitopology {
              description
                "Enable Multicast-Specific RPF Topology";
              type empty;
            }
          }
        }
        container ipv6 {
          description
            "VRF IPv6 configuration";
          container multicast {
            description
              "IP multicast configuration";
            leaf multitopology {
              description
                "Enable Multicast-Specific RPF Topology";
              type empty;
            }
          }
        }
        leaf rd {
          description
            "Specify Route Distinguisher";
          type ios-types:asn-ip-type;
        }
        container address-family {
          description
            "Enter Address Family command mode";
          container ipv4 {
            description
              "Address family";
            presence "true";
            container export {
              description
                "VRF export";
              leaf map {
                description
                  "WORD;;Route-map reference";
                must '../../../../rd' {
                  error-message "%vrf does not have rd configured, please configure rd before configuring export route-map";
                }
                type string;
              }
              container ipv4 {
                description
                  "Address family based VRF import";
                leaf ipv4-type {
                  description
                    "Import prefixes from IPv4 Unicast or Multicast table";
                  must '../../../../../rd' {
                    error-message "%vrf does not have rd configured, please configure rd before configuring export route-map";
                  }
                  type enumeration {
                    enum unicast;
                    enum multicast;
                  }
                }
                leaf upper-limit {
                  description
                    "Upper limit on import prefixes without hogging memory";
                  must '../../../../../rd' {
                    error-message "%vrf does not have rd configured, please configure rd before configuring export route-map";
                  }
                  type uint32 {
                    range "1..2147483647";
                  }
                }
                leaf map {
                  description
                    "Route-map based VRF import";
                  must '(not(.) and not(../../map)) or (. and not(../../map)) or (not(.) and ../../map)' {
                    error-message "map and ipv4 map cannot be configured at the same time";
                  }
                  must '../../../../../rd' {
                    error-message "%vrf does not have rd configured, please configure rd before configuring export route-map";
                  }
                  type string;
                }
                leaf allow-evpn {
                  description
                    "allow EVPN routes into global table";
                  when "(../ipv4-type = 'unicast')";
                  type empty;
                }
              }
            }
            uses vrf-maximum-grouping;
            uses config-mvpn-mdt-grouping;
            uses route-replicate-grouping;
            container route-target {
              description
                "Specify Target VPN Extended Communities";
              when '../../../rd';
              uses vrf-af-route-target-grouping;
            }
            container bgp {
              description
                "Commands pertaining to BGP";
              container next-hop {
                description
                  "Next-hop for the routes of a VRF in the backbone";
                uses vrf-loopback-grouping;
              }
            }
            container import {
              description
                "VRF import";
              leaf map {
                description
                  "Route-map based VRF import";
                type string;
              }
              container ipv4 {
                description
                  "Address family based VRF import";
                leaf ipv4-type {
                  description
                    "Import prefixes from IPv4 Unicast or Multicast table";
                  must '../../../../../rd' {
                    error-message "%vrf does not have rd configured, please configure rd before configuring export route-map";
                  }
                  type enumeration {
                    enum unicast;
                    enum multicast;
                  }
                }
                leaf upper-limit {
                  description
                    "Upper limit on import prefixes without hogging memory";
                  must '../../../../../rd' {
                    error-message "%vrf does not have rd configured, please configure rd before configuring export route-map";
                  }
                  type uint32 {
                    range "1..2147483647";
                  }
                }
                leaf map {
                  description
                    "Route-map based VRF import";
                  must '(not(.) and not(../../map)) or (. and not(../../map)) or (not(.) and ../../map)' {
                    error-message "map and ipv4 map cannot be configured at the same time";
                  }
                  must '../../../../../rd' {
                    error-message "%vrf does not have rd configured, please configure rd before configuring export route-map";
                  }
                  type string;
                }
                leaf allow-evpn {
                  description
                    "allow Global->VRF routes into EVPN";
                  when "(../ipv4-type = 'unicast')";
                  type empty;
                }
              }
            }
          }
          container ipv6 {
            description
              "Address family";
            presence "true";
            uses vrf-maximum-grouping;
            uses config-mvpn-mdt-grouping;
            container route-target {
              description
                "Specify Target VPN Extended Communities";
              when '../../../rd';
              uses vrf-af-route-target-grouping;
            }
            container bgp {
              description
                "Commands pertaining to BGP";
              container next-hop {
                description
                  "Next-hop for the routes of a VRF in the backbone";
                choice ipv4-ipv6 {
                  container ipv4 {
                    description
                      "Use ipv4 address of the Loopback";
                    uses vrf-loopback-grouping;
                  }
                  container ipv6 {
                    description
                      "Use ipv6 address of the Loopback";
                    uses vrf-loopback-grouping;
                  }
                }
              }
            }
            container import {
              description
                "VRF import";
              leaf map {
                description
                  "Route-map based VRF import";
                type string;
              }
              container ipv6 {
                description
                  "Address family based VRF import";
                leaf ipv6-type {
                  description
                    "Import prefixes from IPv6 Unicast or Multicast table";
                  must '../../../../../rd' {
                    error-message "%vrf does not have rd configured, please configure rd before configuring export route-map";
                  }
                  type enumeration {
                    enum unicast;
                    enum multicast;
                  }
                }
                leaf upper-limit {
                  description
                    "Upper limit on import prefixes without hogging memory";
                  must '../../../../../rd' {
                    error-message "%vrf does not have rd configured, please configure rd before configuring export route-map";
                  }
                  type uint32 {
                    range "1..2147483647";
                  }
                }
                leaf map {
                  description
                    "Route-map based VRF import";
                  must '(not(.) and not(../../map)) or (. and not(../../map)) or (not(.) and ../../map)' {
                    error-message "map and ipv6 map cannot be configured at the same time";
                  }
                  must '../../../../../rd' {
                    error-message "%vrf does not have rd configured, please configure rd before configuring export route-map";
                  }
                  type string;
                }
                leaf allow-evpn {
                  description
                    "allow Global->VRF routes into EVPN";
                  when "(../ipv6-type = 'unicast')";
                  type empty;
                }
              }
            }
            container export {
              description
                "VRF export";
              leaf map {
                description
                  "Route-map based VRF export";
                must '../../../../rd' {
                  error-message "%vrf does not have rd configured, please configure rd before configuring export route-map";
                }
                type string;
              }
              container ipv6 {
                description
                  "Address family based VRF import";
                leaf ipv6-type {
                  description
                    "Import prefixes from IPv6 Unicast or Multicast table";
                  must '../../../../../rd' {
                    error-message "%vrf does not have rd configured, please configure rd before configuring export route-map";
                  }
                  type enumeration {
                    enum unicast;
                    enum multicast;
                  }
                }
                leaf upper-limit {
                  description
                    "Upper limit on import prefixes without hogging memory";
                  must '../../../../../rd' {
                    error-message "%vrf does not have rd configured, please configure rd before configuring export route-map";
                  }
                  type uint32 {
                    range "1..2147483647";
                  }
                }
                leaf map {
                  description
                    "Route-map based VRF import";
                  must '(not(.) and not(../../map)) or (. and not(../../map)) or (not(.) and ../../map)' {
                    error-message "map and ipv6 map cannot be configured at the same time";
                  }
                  must '../../../../../rd' {
                    error-message "%vrf does not have rd configured, please configure rd before configuring export route-map";
                  }
                  type string;
                }
                leaf allow-evpn {
                  description
                    "allow EVPN routes into global table";
                  when "(../ipv6-type = 'unicast')";
                  type empty;
                }
              }
            }
          }
        }
        container route-target {
          description
            "Specify Target VPN Extended Communities";
          when '../rd';
          uses vrf-route-target-grouping;
        }
        container vnet {
          description
            "Virtual NETworking configuration";
          leaf tag {
            description
              "Identifier used to tag packets associated with this VNET";
            type uint16 {
              range "2..4094";
            }
          }
        }
        container vpn {
          description
            "Configure VPN ID as specified in rfc2685";
          leaf id {
            description
              "Configure VPN ID in rfc2685 format";
            type vpn-id-type;
          }
        }
      }
    }
  }

  grouping password-grouping {
    container password-container {
      leaf encryption {
        type uint8 {
          range "0..7";
        }
      }
      leaf password {
        type string {
          pattern '([1-680-9a-zA-Z].*)|(0.+)|(7.+)';
        }
      }
    }
  }

  grouping ip-route-static-bfd-group-grouping {
    leaf group {
      description
        "assign a bfd group";
      type string;
    }
    leaf passive {
      description
        "passive member of the group";
      when '../group';
      type empty;
    }
    leaf log {
      description
        "Log changes in BFD Up/Down events";
      type empty;
    }
    leaf unassociate {
      description
        "Static Route not associated";
      type empty;
    }
  }

  grouping ip-route-static-bfd-ip-grouping {
    list multihop {
      key "destination_ip";
      leaf destination_ip {
        description
          "Multihop BFD Destination IP address";
        type inet:ipv4-address;
      }
      list vrf {
        description
          "Source VRF name";
        key "name source_ip";
        leaf name {
          must "(/ios:native/ios:vrf/ios:definition[ios:name=current()] and
                 /ios:native/ios:vrf/ios:definition[ios:name=current()]/ios:address-family/ios:ipv4) or
                 /ios:native/ios:ip/ios:vrf[ios:name=current()]" {
            error-message "% vrf does not exist. Create first";
          }
          type string;
        }
        leaf source_ip {
          description
            "Multihop BFD Source IP address";
          type inet:ipv4-address;
        }
        uses ip-route-static-bfd-group-grouping;
      }
      list source_ip {
        key "ip";
        leaf ip {
          type inet:ipv4-address;
        }
        uses ip-route-static-bfd-group-grouping;
      }
    }
  }

  grouping ip-route-dhcp-grouping {
    leaf dhcp {
      description
        "Default Gateway obtained from DHCP";
      type empty;
    }
  }

  grouping ip-route-dhcp-only-options-grouping {
    uses ip-route-dhcp-grouping;
    leaf metric {
      type uint8 {
        range "1..255";
      }
      default "1";
    }
  }

  grouping ip-route-options-no-track-grouping {
    leaf metric {
      type uint8 {
        range "1..255";
      }
      default "1";
    }
    leaf global {
      description
        "Next hop address is global";
      type empty;
    }
    leaf name {
      description
        "Specify name of the next hop";
      type string;
    }
    leaf permanent {
      description
        "permanent route";
      type empty;
    }
    leaf multicast {
      description
        "multicast route";
      type empty;
    }
    leaf tag {
      description
        "Set tag for this route";
      type uint32 {
        range "1..4294967295";
      }
    }
  }

  grouping ip-route-options-grouping {
    uses ip-route-options-no-track-grouping;
    leaf track {
      description
        "Install route depending on tracked item";
      type uint16 {
        range "1..1000";
      }
      status deprecated;
    }
  }

  grouping ip-route-options-track-mandatory-grouping {
    uses ip-route-options-no-track-grouping;
    container track-id-name {
      description
        "Install route depending on tracked item";
      choice track-choice {
        mandatory true;
        leaf id {
          description
            "Track number";
          type uint16 {
            range "1..1000";
          }
        }
      }
    }
  }

  grouping ip-route-options-interface-grouping {
    uses ip-route-options-no-track-grouping;
    container track-id-name {
      description
        "Install route depending on tracked item";
      choice track-choice {
        leaf id {
          description
            "Track number";
          type uint16 {
            range "1..1000";
          }
        }
      }
    }
    leaf track {
      description
        "Install route depending on tracked item";
      type uint16 {
        range "1..1000";
      }
      status deprecated;
    }
  }

  grouping ip-route-srte-options-grouping {
    leaf metric {
      type uint8 {
        range "1..255";
      }
      default "1";
    }
    leaf name {
      description
        "Specify name of the next hop";
      type string {
        length "1..255";
      }
    }
    leaf tag {
      description
        "Set tag for this route";
      type uint32 {
        range "1..4294967295";
      }
    }
  }

  grouping ip-route-grouping-min-elements {
    list ip-route-interface-forwarding-list {
      key "prefix mask";
      min-elements 1;
      leaf prefix {
        type inet:ipv4-address;
      }
      leaf mask {
        type inet:ipv4-address;
      }
      uses ip-route-dhcp-only-options-grouping;
      list fwd-list {
        key "fwd";
        leaf fwd {
          type union {
            type enumeration {
              enum Null0;
            }
            type inet:ipv4-address;
            type string;
          }
        }
        list interface-next-hop {
          key "ip-address";
          leaf ip-address {
            type inet:ipv4-address;
          }
          uses ip-route-options-interface-grouping;
        }
        uses ip-route-options-grouping;
      }
      list fwd-list-with-track {
        key "fwd";
        leaf fwd {
          type union {
            type enumeration {
              enum Null0;
            }
            type inet:ipv4-address;
            type string;
          }
        }
        uses ip-route-options-track-mandatory-grouping;
      }
    }
  }

  grouping ip-route-fwd-list-key-grouping {
    leaf fwd {
      type union {
        type enumeration {
          enum Null0;
        }
        type inet:ipv4-address;
        type string;
      }
      must "not (starts-with(., 'Dialer')) or /ios:native/ios:interface/*[concat(local-name(), ios:name) = current()]" {
        error-message "Dialer interface must be created first and deleted last.";
      }
      must "not (starts-with(., 'Loopback')) or /ios:native/ios:interface/*[concat(local-name(), ios:name) = current()]" {
        error-message "Loopback interface must be created first and deleted last.";
      }
      must "not (starts-with(., 'Tunnel')) or /ios:native/ios:interface/*[concat(local-name(), ios:name) = current()]" {
        error-message "Tunnel interface must be created first and deleted last.";
      }
      must "not (starts-with(., 'Port-channel')) or /ios:native/ios:interface/*[concat(local-name(), ios:name) = current()]" {
        error-message "Port-channel interface must be created first and deleted last.";
      }
      must "not (starts-with(., 'Vlan')) or /ios:native/ios:interface/*[concat(local-name(), ios:name) = current()]" {
        error-message "Vlan interface must be created first and deleted last.";
      }
      must "not (starts-with(., 'LISP')) or /ios:native/ios:interface/*[concat(local-name(), ios:name) = current()]" {
        error-message "LISP interface must be created first and deleted last.";
      }
      must "not (starts-with(., 'Virtual-Template')) or /ios:native/ios:interface/*[concat(local-name(), ios:name) = current()]" {
        error-message "Virtual-Template interface must be created first and deleted last.";
      }
      must "not (starts-with(., 'BDI')) or /ios:native/ios:interface/*[concat(local-name(), ios:name) = current()]" {
        error-message "BDI interface must be created first and deleted last.";
      }
      must "not (starts-with(., 'Ethernet')) or /ios:native/ios:interface/*[concat(local-name(), ios:name) = current()]" {
        error-message "Ethernet interface must be created first and deleted last.";
      }
      must "not (starts-with(., 'FastEthernet')) or /ios:native/ios:interface/*[concat(local-name(), ios:name) = current()]" {
        error-message "FastEthernet interface must be created first and deleted last.";
      }
      must "not (starts-with(., 'GigabitEthernet')) or /ios:native/ios:interface/*[concat(local-name(), ios:name) = current()]" {
        error-message "GigabitEthernet interface must be created first and deleted last.";
      }
      must "not (starts-with(., 'TenGigabitEthernet')) or /ios:native/ios:interface/*[concat(local-name(), ios:name) = current()]" {
        error-message "TenGigabitEthernet interface must be created first and deleted last.";
      }
      must "not (starts-with(., 'FiveGigabitEthernet')) or /ios:native/ios:interface/*[concat(local-name(), ios:name) = current()]" {
        error-message "FiveGigabitEthernet interface must be created first and deleted last.";
      }
      must "not (starts-with(., 'TwentyFiveGigE')) or /ios:native/ios:interface/*[concat(local-name(), ios:name) = current()]" {
        error-message "TwentyFiveGigE interface must be created first and deleted last.";
      }
      must "not (starts-with(., 'TwoGigabitEthernet')) or /ios:native/ios:interface/*[concat(local-name(), ios:name) = current()]" {
        error-message "TwoGigabitEthernet interface must be created first and deleted last.";
      }
      must "not (starts-with(., 'FortyGigabitEthernet')) or /ios:native/ios:interface/*[concat(local-name(), ios:name) = current()]" {
        error-message "FortyGigabitEthernet interface must be created first and deleted last.";
      }
      must "not (starts-with(., 'HundredGigE')) or /ios:native/ios:interface/*[concat(local-name(), ios:name) = current()]" {
        error-message "HundredGigE interface must be created first and deleted last.";
      }
    }
  }

  grouping ip-route-grouping {
    list ip-route-interface-forwarding-list {
      key "prefix mask";
      leaf prefix {
        type inet:ipv4-address;
      }
      leaf mask {
        type inet:ipv4-address;
      }
      uses ip-route-dhcp-only-options-grouping;
      list fwd-list {
        key "fwd";
        uses ip-route-fwd-list-key-grouping;
        list interface-next-hop {
          key "ip-address";
          leaf ip-address {
            type inet:ipv4-address;
          }
          uses ip-route-options-interface-grouping;
        }
        uses ip-route-dhcp-grouping;
        uses ip-route-options-grouping;
      }
      list fwd-list-with-track {
        key "fwd";
        uses ip-route-fwd-list-key-grouping;
        uses ip-route-dhcp-grouping;
        uses ip-route-options-track-mandatory-grouping;
      }
      uses ip-route-segment-routing-grouping;
    }
  }

  grouping ip-route-segment-routing-grouping {
    container segment-routing {
      list policy {
        key "srname";
        leaf srname {
          type string {
            length "1..64";
          }
        }
        uses ip-route-srte-options-grouping;
      }
    }
  }

  grouping ip-exp-path-mode-cfg-grouping {
    list index {
      description
        "Specify the next entry index to add, edit (or delete): <1..65535>";
      key "idx";
      leaf idx {
        type uint32 {
          range "1..65535";
        }
      }
      choice ip-exp-path-option {
        container next-address {
          description
            "Specify the next address in the path";
          leaf loose {
            description
              "Target IPv4 address is loose";
            type empty;
          }
          leaf ipv4 {
            description
              "Target IPv4 address (strict)";
            type inet:ipv4-address;
          }
        }
        leaf next-label {
          description
            "Specify the next MPLS label in the path: <0..1048575>";
          type uint32 {
            range "0..1048575";
          }
        }
        leaf exclude-address {
          description
            "Exclude an address from subsequent partial path segments";
          type inet:ipv4-address;
        }
        leaf exclude-srlg {
          description
            "Specify an address to get SRLGs from for exclusion";
          type inet:ipv4-address;
        }
      }
    }
  }

  grouping config-ip-ssh-algorithm-grouping {
    container algorithm {
      description
        "Configure different algorithms used in SSH";
      container encryption {
        description
          "Encryption algorithms advertised to other party";
        leaf aes128-ctr {
          description
            "AES with 128-bit key in CTR mode";
          type empty;
        }
        leaf aes192-ctr {
          description
            "AEC with 192-bit key in CTR mode";
          type empty;
        }
        leaf aes256-ctr {
          description
            "AEC with 256-bit key in CTR mode";
          type empty;
        }
      }
    }
  }

  grouping config-ip-grouping {
    container ip {
      description
        "Global IP configuration subcommands";
      container ospf {
        description
          "Configure for ospf";
        leaf name-lookup {
          description
            "Display OSPF router ids as DNS names";
          type empty;
        }
      }
      container admission {
        description
          "Network Admission Control (NAC)";
        container watch-list {
          description
            "Watch-list";
          leaf expiry-time {
            description
              "Configure expiry time for watch-list entries";
            type uint16 {
              range "0..35791";
            }
          }
        }
        container name {
          description
            "Specify an Authentication Proxy Rule";
          container webauth {
            description
              "help";
            container proxy {
              description
                "Authentication Proxy Protocol";
              leaf http {
                description
                  "HTTP Protocol";
                type empty;
              }
            }
          }
        }
      }
      container arp {
        description
          "IP ARP global configuration";
        container incomplete {
          description
            "Fine-tune the ARP Retry parameters";
          leaf entries {
            description
              "Specify the number of IP addresses to resolve";
            type uint32 {
              range "1..2147483647";
            }
          }
        }
        container inspection {
          description
            "Arp Inspection configuration";
          list filter {
            description
              "Specify ARP acl to be applied";
            key "arpacl";
            leaf arpacl {
              type string;
            }
            list vlan {
              description
                "Vlans to apply the filter";
              key "vlan-range";
              leaf vlan-range {
                type string;
              }
              leaf static {
                description
                  "Apply the ACL statically";
                type empty;
              }
            }
          }
          container validate {
            description
              "Validate addresses";
            leaf src-mac {
              description
                "Validate source MAC address";
              type empty;
            }
            leaf dst-mac {
              description
                "Validate destination MAC address";
              type empty;
            }
            leaf ip {
              description
                "Validate IP addresses";
              type empty;
            }
            container allow {
              leaf zeros {
                description
                  "Allow 0.0.0.0 sender IP address";
                type empty;
              }
            }
          }
          container log-buffer {
            description
              "Log Buffer Configuration";
            leaf entries {
              description
                "Number of entries for log buffer";
              type uint16 {
                range "0..1024";
              }
            }
            container logs {
              description
                "Number of logs per interval";
              leaf entries {
                description
                  "Number of entries for log buffer";
                type uint16 {
                  range "0..1024";
                }
              }
              leaf interval {
                description
                  "Interval for controlling logging rate";
                type uint32 {
                  range "0..86400";
                }
              }
            }
          }
          leaf vlan {
            description
              "Enable/Disable ARP Inspection on vlans";
            type string;
          }
        }
        container proxy {
          description
            "Gratuitous ARP control";
          leaf disable {
            description
              "Disable proxy ARP on all interfaces";
            type empty;
          }
        }
        container entry {
          description
            "Global ARP table learn entry";
          leaf learn {
            description
              "Maximum learn entry limit";
            type uint32 {
              range "255..512000";
            }
          }
        }
      }
      container domain-list {
        description
          "Domain name to complete unqualified host names";
        status obsolete;
        leaf domain-name {
          status obsolete;
          type string;
        }
        container vrf {
          description
            "Specify VRF";
          status obsolete;
          leaf vrf-name {
            status obsolete;
            type string;
          }
          leaf domain-name {
            status obsolete;
            type string;
          }
        }
      }
      container finger {
        description
          "finger server";
        presence "true";
      }
      container rcmd {
        description
          "Rcmd commands";
        leaf rcp-enable {
          description
            "Enable server side of RCP";
          type empty;
        }
        leaf rsh-enable {
          description
            "Enable server side of RSh";
          type empty;
        }
        leaf domain-lookup {
          description
            "Enable IP DNS queries for Rcmd";
          when "../../domain/lookup = 'true'";
          type boolean;
          default "true";
        }
      }
      leaf subnet-zero {
        description
          "Allow 'subnet zero' subnets";
        type boolean;
      }
      container bgp-community {
        description
          "format for BGP community";
        leaf new-format {
          description
            "select aa:nn format for BGP community";
          type empty;
        }
      }
      leaf host-routing {
        description
          "Enable host-based routing (proxy ARP and redirect)";
        type empty;
      }
      list vrf {
        description
          "Configure an IP VPN Routing/Forwarding instance";
        key "name";
        leaf name {
          description
            "WORD;;VPN Routing/Forwarding instance name";
          type string;
        }
        container bgp {
          description
            "Commands pertaining to BGP";
          container next-hop {
            description
              "Next-hop for the routes of a VRF in the backbone";
            leaf Loopback {
              description
                "Loopback interface number";
              type uint32 {
                range "0..2147483647";
              }
            }
          }
        }
        leaf context {
          description
            "Associate SNMP context with this vrf";
          type string;
        }
        leaf description {
          description
            "VRF specific description";
          type string {
            length "1..244";
          }
        }
        leaf rd {
          description
            "Specify Route Distinguisher";
          type rd-type;
        }
        container export {
          description
            "VRF export";
          leaf map {
            description
              "Route-map based VRF export";
            type string;
          }
          container ipv4 {
            description
              "Address family based VRF export";
            leaf ipv4-type {
              type enumeration {
                enum unicast;
                enum multicast;
              }
            }
            choice map-choice {
              case upper-limit-case {
                leaf upper-limit {
                  type uint32 {
                    range "1..2147483647";
                  }
                }
                leaf map {
                  description
                    "Route-map based VRF export";
                  type string;
                }
              }
              case map-only-case {
                leaf map-only {
                  description
                    "Route-map based VRF export";
                  type string;
                }
              }
            }
          }
        }
        container import {
          description
            "VRF import";
          choice import-choice {
            leaf map {
              description
                "Route-map based VRF import";
              type string;
            }
            container ipv4 {
              description
                "Address family based VRF import";
              leaf ipv4-type {
                type enumeration {
                  enum unicast;
                  enum multicast;
                }
              }
              leaf upper-limit {
                type uint32 {
                  range "1..2147483647";
                }
              }
              leaf map {
                description
                  "Route-map based VRF import";
                type string;
              }
            }
          }
        }
        uses vrf-maximum-grouping;
        container mdt {
          description
            "Backbone Multicast Distribution Tree";
          presence "Backbone Multicast Distribution Tree";
          leaf default {
            description
              "The default group";
            type inet:ipv4-address;
          }
          leaf log-reuse {
            description
              "Event logging for data MDT reuse";
            type empty;
          }
          container data {
            description
              "MDT data group range";
            leaf mulicast-address {
              type inet:ipv4-address;
            }
            leaf wildcard-bits {
              type inet:ipv4-address;
            }
            choice mdt-data-choice {
              case mdt-data-threshold {
                leaf threshold {
                  description
                    "MDT switching threshold";
                  type uint32 {
                    range "1..4294967";
                  }
                }
                leaf threshold-list {
                  description
                    "Access-list";
                  type mdt-data-list-type;
                }
              }
              case mdt-data-list {
                leaf list {
                  description
                    "Access-list";
                  type mdt-data-list-type;
                }
              }
            }
          }
        }
        uses route-replicate-grouping;
        list route-target {
          description
            "Specify Target VPN Extended Communities";
          key "direction target";
          leaf direction {
            type enumeration {
              enum both;
              enum export;
              enum import;
            }
          }
          leaf target {
            type rd-type;
          }
        }
        container vpn {
          description
            "Configure VPN ID as specified in rfc2685";
          leaf id {
            description
              "Configure VPN ID in rfc2685 format";
            type vpn-id-type;
          }
        }
      }
      container as-path {
        description
          "BGP autonomous system path filter";
      }
      container local {
        description
          "Specify local options";
        container policy {
          description
            "Enable policy routing";
          leaf route-map {
            description
              "Policy route map";
            type string;
          }
        }
        list pool {
          description
            "IP Local address pool lists";
          key "id";
          leaf id {
            type union {
              type string;
              type enumeration {
                enum default;
              }
            }
          }
          leaf start {
            type inet:ipv4-address;
          }
          leaf last {
            type inet:ipv4-address;
          }
          leaf group {
            description
              "Create ip local pool group";
            type string;
          }
        }
      }
      container cef {
        description
          "Cisco Express Forwarding";
        presence "true";
      }
      leaf classless {
        description
          "Follow classless routing forwarding rules";
        type empty;
      }
      container domain {
        description
          "IP DNS Resolver";
        container list {
          description
            "Domain name to complete unqualified host names";
          leaf-list domain-name {
            type string;
          }
          container vrf {
            description
              "Specify VRF";
            leaf vrf-name {
              type string;
            }
            leaf domain-name {
              type string;
            }
          }
        }
        leaf lookup {
          description
            "Enable IP Domain Name System hostname translation";
          type boolean;
          default "true";
        }
        container lookup-settings {
          container lookup {
            description
              "Enable IP Domain Name System hostname translation";
            leaf nsap {
              description
                "Enable IP DNS queries for CLNS NSAP addresses";
              type empty;
            }
            leaf recursive {
              description
                "Enable IP DNS recursive lookup";
              type empty;
            }
            list vrf {
              description
                "Specify VRF";
              key "vrf-name";
              leaf vrf-name {
                description
                  "VRF name";
                type string;
              }
              container source-interface {
                description
                  "Specify source interface for DNS resolver";
                uses ios-ifc:interface-grouping;
              }
            }
            container source-interface {
              description
                "Specify source interface for DNS resolver";
              uses ios-ifc:interface-grouping;
            }
          }
          leaf name {
            description
              "Define the default domain name";
            type string;
          }
        }
        leaf name {
          description
            "Define the default domain name";
          type string;
        }
        leaf periodic-resolve {
          description
            "Specify periodicity for DNS resolution";
          type uint32 {
            range "30..3000";
          }
          default "240";
        }
        leaf timeout {
          description
            "Specify timeout waiting for response to a DNS query";
          type uint16 {
            range "1..3600";
          }
          units "seconds";
          default "5";
        }
      }
      container domain-lookup-conf {
        status obsolete;
        leaf domain-lookup {
          status obsolete;
          type boolean;
        }
      }
      container domain-lookup {
        description
          "Enable IP Domain Name System hostname translation";
        presence "true";
        status obsolete;
        leaf nsap {
          description
            "Enable IP DNS queries for CLNS NSAP addresses";
          status obsolete;
          type empty;
        }
        container source-interface {
          description
            "Specify source interface for DNS resolver";
          status obsolete;
          uses ios-ifc:interface-grouping;
        }
      }
      container dns {
        description
          "Configure DNS server for a zone";
        container server {
          description
            "Enable DNS server";
          presence "true";
        }
      }
      leaf default-gateway {
        description
          "Specify default gateway (if not routing IP)";
        type inet:ipv4-address;
      }
      container dhcp {
        description
          "Configure DHCP server and relay parameters";
      }
      container forward-protocol {
        description
          "Controls forwarding of physical and directed IP broadcasts";
        choice protocol-choice {
          leaf protocol {
            type enumeration {
              enum nd;
              enum sdns;
              enum turbo-flood;
            }
          }
          container spanning-tree {
            description
              "Use transparent bridging to flood UDP broadcasts";
            presence "true";
            leaf any-local-broadcast {
              description
                "Accept any local broadcast when flooding";
              type empty;
            }
          }
          container udp {
            description
              "Packets to a specific UDP port";
            leaf biff {
              description
                "Biff (mail notification, comsat, 512)";
              type boolean;
            }
            leaf bootpc {
              description
                "Bootstrap Protocol (BOOTP) client (68)";
              type boolean;
            }
            leaf bootps {
              description
                "Bootstrap Protocol (BOOTP) server (67)";
              type boolean;
            }
            leaf discard {
              description
                "Discard (9)";
              type boolean;
            }
            leaf dnsix {
              description
                "DNSIX security protocol auditing (195)";
              type boolean;
            }
            leaf domain {
              description
                "Domain Name Service (DNS, 53)";
              type boolean;
            }
            leaf echo {
              description
                "Echo (7)";
              type boolean;
            }
            leaf isakmp {
              description
                "Internet Security Association and Key Management Protocol(500)";
              type boolean;
            }
            leaf mobile-ip {
              description
                "Mobile IP registration (434)";
              type boolean;
            }
            leaf nameserver {
              description
                "IEN116 name service (obsolete, 42)";
              type boolean;
            }
            leaf netbios-dgm {
              description
                "NetBios datagram service (138)";
              type boolean;
            }
            leaf netbios-ns {
              description
                "NetBios name service (137)";
              type boolean;
            }
            leaf netbios-ss {
              description
                "NetBios session service (139)";
              type boolean;
            }
            leaf non500-isakmp {
              description
                "Internet Security Association and Key Management Protocol(4500)";
              type boolean;
            }
            leaf ntp {
              description
                "Network Time Protocol (123)";
              type boolean;
            }
            leaf pim-auto-rp {
              description
                "PIM Auto-RP (496)";
              type boolean;
            }
            leaf rip {
              description
                "Routing Information Protocol (router, in.routed, 520)";
              type boolean;
            }
            leaf snmp {
              description
                "Simple Network Management Protocol (161)";
              type boolean;
            }
            leaf snmptrap {
              description
                "SNMP Traps (162)";
              type boolean;
            }
            leaf sunrpc {
              description
                "Sun Remote Procedure Call (111)";
              type boolean;
            }
            leaf syslog {
              description
                "System Logger (514)";
              type boolean;
            }
            leaf tacacs {
              description
                "TAC Access Control System (49)";
              type boolean;
            }
            leaf talk {
              description
                "Talk (517)";
              type boolean;
            }
            leaf tftp {
              description
                "Trivial File Transfer Protocol (69)";
              type boolean;
            }
            leaf time {
              description
                "Time (37)";
              type boolean;
            }
            leaf who {
              description
                "Who service (rwho, 513)";
              type boolean;
            }
            leaf xdmcp {
              description
                "X Display Manager Control Protocol (177)";
              type boolean;
            }
          }
        }
      }
      container gratuitous-arps-conf {
        leaf gratuitous-arps {
          description
            "Generate gratuitous ARPs for PPP/SLIP peer addresses";
          type boolean;
        }
      }
      container ftp {
        description
          "FTP configuration commands";
        container source-interface {
          description
            "Specify interface for source address in FTP connections";
          uses ios-ifc:interface-grouping;
        }
        leaf passive-enable {
          description
            "Connect using passive mode";
          type boolean;
          default "true";
        }
        leaf passive {
          status deprecated;
          description
            "Connect using passive mode, deprecated and replaced by passive-enable";
          type empty;
        }
        container password {
          description
            "Specify password for FTP connections;";
          uses password-grouping;
        }
        leaf username {
          description
            "Specify username for FTP connections";
          type string;
        }
      }
      container telnet {
        description
          "Specify telnet options";
        leaf source-interface {
          description
            "Specify source interface";
          type string;
        }
      }
      container host {
        description
          "Add an entry to the ip hostname table";
        list host-list {
          key "name";
          leaf name {
            description
              "Name of host";
            type string;
          }
          leaf-list ip-list {
            description
              "Host IP address";
            type inet:ip-address;
          }
        }
        list vrf {
          description
            "Specify VRF";
          key "vrf-name";
          leaf vrf-name {
            description
              "VRF name";
            type string;
          }
          list host-name {
            description
              "Name of host";
            key "host-name";
            leaf host-name {
              description
                "Name of host";
              type string;
            }
            leaf-list ip-list {
              description
                "Host IP address";
              ordered-by user;
              max-elements 14;
              type inet:ip-address;
            }
          }
        }
      }
      container multicast {
        description
          "Global IP Multicast Commands";
      }
      container name-server {
        leaf-list no-vrf {
          max-elements 6;
          type union {
            type inet:ipv4-address;
            type inet:ipv6-address;
          }
        }
        list vrf {
          description
            "";
          key "word";
          leaf word {
            type string;
          }
          leaf-list server-ip-list {
            max-elements 6;
            type union {
              type inet:ipv4-address;
              type inet:ipv6-address;
            }
          }
          leaf server-ip {
            status deprecated;
            type union {
              type inet:ipv4-address;
              type inet:ipv6-address;
            }
          }
        }
      }
      container pim {
        description
          "PIM global commands";
      }
      grouping ip-prefix-lists-grouping {
        list prefix-only-list {
          description
            "Prefix lists without sequence numbers";
          ordered-by user;
          key "prefix";
          leaf prefix {
            description
              "IPv4 Prefix";
            type inet:ipv4-prefix;
          }
        }
        list prefix-ge-list {
          description
            "Combination of prefix with ge entries";
          ordered-by user;
          key "prefix ge";
          leaf prefix {
            description
              "IPv4 Prefix";
            type inet:ipv4-prefix;
          }
          leaf ge {
            description
              "Minimum prefix length to be matched";
            type uint8 {
              range "1..32";
            }
          }
        }
        list prefix-le-list {
          description
            "Combination of prefix with le entries";
          ordered-by user;
          key "prefix le";
          leaf prefix {
            description
              "IPv4 Prefix";
            type inet:ipv4-prefix;
          }
          leaf le {
            description
              "Maximum prefix length to be matched";
            type uint8 {
              range "1..32";
            }
          }
        }
        list prefix-ge-le-list {
          description
            "Combination of prefix with ge and le entries";
          ordered-by user;
          key "prefix ge le";
          leaf prefix {
            description
              "IPv4 Prefix";
            type inet:ipv4-prefix;
          }
          leaf ge {
            description
              "Minimum prefix length to be matched";
            type uint8 {
              range "1..32";
            }
          }
          leaf le {
            description
              "Maximum prefix length to be matched";
            type uint8 {
              range "1..32";
            }
          }
        }
      }

      container prefix-lists {
        description
          "Build a prefix list";
        list name-only-prefixes {
          description
            "Build a prefix list without sequence number";
          if-feature "ios-features:prefixlist-controller";
          key "name";
          leaf name {
            description
              "Name of the prefix-list";
            type string {
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          container permit {
            description
              "Specify packets to forward";
            uses ip-prefix-lists-grouping;
          }
          container deny {
            description
              "Specify packets to reject";
            uses ip-prefix-lists-grouping;
          }
        }
        list prefixes {
          description
            "Build prefix-lists with name ans seq.no";
          key "name no";
          leaf name {
            description
              "Name of the prefix-list";
            type string {
              pattern '([^s].*)|(s[^e].*)|(se[^q].*)|(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf no {
            description
              "Seq Number of the prefix-list";
            type uint32 {
              range "1..4294967294";
            }
          }
          leaf action {
            description
              "Specify deny or permit action";
            type enumeration {
              enum permit;
              enum deny;
            }
          }
          leaf ip {
            description
              "IPv4 Prefix";
            type inet:ipv4-prefix;
          }
          leaf ge {
            description
              "Minimum prefix length to be matched";
            type uint8 {
              range "1..32";
            }
          }
          leaf le {
            description
              "Maximum prefix length to be matched";
            type uint8 {
              range "1..32";
            }
          }
        }
        list prefix-list-description {
          description
            "Describe about prefix-list entry";
          key "name";
          leaf name {
            type string {
              pattern '([^s].*)|(s[^e].*)|(se[^q].*)|(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            description
              "Prefix-list specific description";
            type string {
              length "1..80";
            }
          }
        }
        leaf sequence-number {
          description
            "Include/exclude sequence numbers in NVGEN";
          type empty;
        }
      }
      container prefix-list {
        status deprecated;
        if-feature "ios-features:prefixlist-autonomous";
        description
          "Build a prefix list (DEPRECATED)";
        list prefixes {
          status deprecated;
          key "name";
          leaf name {
            status deprecated;
            type string {
              pattern '([^s].*)|(s[^e].*)|(se[^q].*)|(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            status deprecated;
            description
              "Prefix-list specific description (DEPRECATED)";
            type string {
              length "1..80";
            }
          }
          list seq {
            status deprecated;
            description
              "sequence number of an entry (DEPRECATED)";
            key "no";
            leaf no {
              status deprecated;
              type uint32 {
                range "1..4294967294";
              }
            }
            leaf action {
              status deprecated;
              type enumeration {
                enum permit;
                enum deny;
              }
            }
            leaf ip {
              status deprecated;
              type inet:ipv4-prefix;
            }
            leaf ge {
              status deprecated;
              description
                "Minimum prefix length to be matched (DEPRECATED)";
              type uint8 {
                range "1..32";
              }
            }
            leaf le {
              status deprecated;
              description
                "Maximum prefix length to be matched (DEPRECATED)";
              type uint8 {
                range "1..32";
              }
            }
          }
        }
        leaf sequence-number {
          status deprecated;
          description
            "Include/exclude sequence numbers in NVGEN (DEPRECATED)";
          type empty;
        }
      }
      container route {
        description
          "Establish static routes";
        uses ip-route-grouping;
        leaf profile {
          description
            "Enable IP routing table profile";
          type empty;
        }
        container static {
          description
            "Allow static routes";
          leaf adjust-time {
            description
              "Time period for adjusting static routes";
            type uint8 {
              range "1..60";
            }
          }
          container bfd {
            description
              "BFD tracked";
            list interface {
              key "name gateway_ip";
              leaf name {
                type union {
                  type enumeration {
                    enum Null0;
                  }
                  type string;
                }
              }
              leaf gateway_ip {
                description
                  "Gateway IP address";
                type inet:ipv4-address;
              }
              uses ip-route-static-bfd-group-grouping;
            }
            uses ip-route-static-bfd-ip-grouping;
            list vrf {
              description
                "Destination VRF name";
              key "name";
              leaf name {
                must "(/ios:native/ios:vrf/ios:definition[ios:name=current()] and
                       /ios:native/ios:vrf/ios:definition[ios:name=current()]/ios:address-family/ios:ipv4) or
                       /ios:native/ios:ip/ios:vrf[ios:name=current()]" {
                  error-message "% vrf does not exist. Create first";
                }
                type string;
              }
              uses ip-route-static-bfd-ip-grouping;
            }
          }
          container install-routes-recurse-via-nexthop {
            description
              "installing recursive route next hop";
            leaf all {
              description
                "Configure for all default topologies";
              type empty;
            }
            container recurse-nexthop {
              description
                "Recursive route next hop's";
              list topology {
                key "topology-id";
                leaf topology-id {
                  description
                    "Configure recursive static route for a Topology";
                  type string;
                }
                uses routes-recurse-grouping;
              }
              list vrf {
                key "vrf-id";
                leaf vrf-id {
                  description
                    "Configure static route for a VPN Routing/Forwarding instance";
                  type string;
                }
                uses routes-recurse-grouping;
              }
              uses routes-recurse-grouping;
            }
            leaf install-routes-recurse-via-nexthop {
              description
                "installing recursive route next hop";
              type empty;
            }
          }
          leaf inter-vrf {
            description
              "Across VRF interfaces";
            type empty;
          }
        }
        list vrf {
          description
            "Configure static route for a VPN Routing/Forwarding instance";
          key "name";
          leaf name {
            must '(/ios:native/ios:vrf/ios:definition[ios:name=current()] and /ios:native/ios:vrf/ios:definition[ios:name=current()]/ios:address-family/ios:ipv4) or /ios:native/ios:ip/ios:vrf[ios:name=current()]' {
              error-message "Please create ipv4 vrf first, and delete the last";
            }
            type string;
          }
          list topology {
            description
              "Configure static route for a Topology Routing/Forwarding instance";
            key "name";
            leaf name {
              must "not (current() = 'base')" {
                error-message "only non 'base' topology is allowed";
              }
              type string;
            }
            list ip-route-interface-forwarding-list {
              key "prefix mask";
              leaf prefix {
                type inet:ipv4-address;
              }
              leaf mask {
                type inet:ipv4-address;
              }
              uses ip-route-dhcp-only-options-grouping;
              list fwd-list {
                key "fwd";
                leaf fwd {
                  type union {
                    type enumeration {
                      enum Null0;
                    }
                    type inet:ipv4-address;
                    type string;
                  }
                }
                list interface-next-hop {
                  key "ip-address";
                  leaf ip-address {
                    type inet:ipv4-address;
                  }
                  uses ip-route-options-interface-grouping {
                    refine "multicast" {
                      mandatory true;
                    }
                  }
                }
                uses ip-route-options-grouping {
                  refine "multicast" {
                    mandatory true;
                  }
                }
              }
              list fwd-list-with-track {
                key "fwd";
                leaf fwd {
                  type union {
                    type enumeration {
                      enum Null0;
                    }
                    type inet:ipv4-address;
                    type string;
                  }
                }
                uses ip-route-options-track-mandatory-grouping {
                  refine "multicast" {
                    mandatory true;
                  }
                }
              }
            }
          }
          uses ip-route-grouping-min-elements;
        }
        list topology {
          description
            "Configure static route for a Topology Routing/Forwarding instance";
          key "name";
          leaf name {
            must "not (current() = 'base')" {
              error-message "only non 'base' topology is allowed";
            }
            type string;
          }
          uses ip-route-grouping;
        }
      }
      container routing-conf {
        description
          "IP routing configuration";
        leaf routing {
          description
            "Enable or disable IP routing";
          type boolean;
          default "true";
        }
      }
      container routing-new {
        description
          "IP routing options";
        when "(../routing-conf/routing = 'true')";
        container routing {
          description
            "IP routing options";
          container protocol {
            description
              "IP routing protocol";
            container purge {
              description
                "routes purge";
              leaf interface {
                description
                  "Perform IP routing protocol routes purge on link failures";
                type boolean;
                default "true";
              }
            }
          }
        }
      }
      container routing {
        status obsolete;
        description
          "This node is obsolete and replaced by routing-new and routing-conf";
        presence "true";
        container protocol {
          status obsolete;
          description
            "IP routing protocol";
          container purge {
            status obsolete;
            description
              "routes purge";
            leaf interface {
              status obsolete;
              description
                "Perform IP routing protocol routes purge on link failures";
              type boolean;
            }
          }
        }
      }
      container explicit-path {
        description
          "Configure explicit-path";
        list identifier {
          description
            "Specify explicit path by number: <1..65535>";
          key "pnum";
          leaf pnum {
            type uint16 {
              range "1..65535";
            }
          }
          leaf mode {
            type enumeration {
              enum enable;
              enum disable;
            }
          }
          uses ip-exp-path-mode-cfg-grouping;
        }
        list name {
          description
            "Specify explicit path by name";
          key "pname";
          leaf pname {
            type string;
          }
          leaf mode {
            type enumeration {
              enum enable;
              enum disable;
            }
          }
          uses ip-exp-path-mode-cfg-grouping;
        }
      }
      container scp {
        description
          "Scp commands";
        container server {
          description
            "Configure SCP server-side functionality";
          leaf enable {
            description
              "Enable server side of SCP";
            type empty;
          }
        }
      }
      container spd {
        description
          "spd";
        leaf mode {
          type enumeration {
            enum aggressive;
          }
        }
        container queue {
          description
            "queue";
          leaf max-threshold {
            description
              "Max threshold";
            type uint16 {
              range "0..65535";
            }
          }
          leaf min-threshold {
            description
              "Min threshold";
            must '. < ../max-threshold' {
              error-message "min-threshold must be less than max-threshold";
            }
            type uint16 {
              range "0..65535";
            }
          }
        }
      }
      container bootp {
        description
          "Config BOOTP services";
        leaf server {
          description
            "Enable BOOTP server";
          type boolean;
        }
      }
      leaf source-route {
        description
          "Process packets with source routing header options";
        type boolean;
      }
      container ssh {
        description
          "Configure ssh options";
        leaf authentication-retries {
          description
            "Specify number of authentication retries";
          type uint8 {
            range "0..5";
          }
        }
        container client {
          description
            "Configuration for client";
          uses config-ip-ssh-algorithm-grouping;
        }
        leaf dscp {
          description
            "IP DSCP value for SSH traffic";
          type uint8 {
            range "0..63";
          }
        }
        container dh {
          description
            "Diffie-Hellman";
          container min {
            description
              "minimum";
            leaf size {
              description
                "key size";
              type enumeration {
                enum 2048;
                enum 4096;
              }
              default "2048";
            }
          }
        }
        container logging {
          description
            "Configure logging for SSH";
          leaf events {
            description
              "Log SSH events";
            type empty;
          }
        }
        container pubkey-chain {
          description
            "Configure public key-chain parameters";
          list username {
            max-elements 15;
            key "name";
            leaf name {
              type string;
            }
            list key-hash {
              max-elements 2;
              key "key-type key-hash-value";
              leaf key-type {
                type enumeration {
                  enum ssh-rsa;
                }
              }
              leaf key-hash-value {
                type string;
              }
            }
          }
        }
        leaf precedence {
          description
            "IP Precedence value for SSH traffic";
          type uint8 {
            range "0..7";
          }
        }
        container rsa {
          description
            "Configure RSA keypair name for SSH";
          leaf keypair-name {
            description
              "keypair-name";
            type string;
          }
        }
        container server {
          description
            "Configuration for server";
          uses config-ip-ssh-algorithm-grouping;
          container peruser {
            description
              "Per User configuration";
            container session {
              description
                "Per User Session";
              leaf limit {
                description
                  "Per User Session Limit";
                type uint8 {
                  range "1..16";
                }
              }
            }
          }
        }
        container source-interface-config {
          description
            "Specify interface for source address in SSH connections";
          uses ios-ifc:interface-grouping;
        }
        leaf source-interface {
          status deprecated;
          description
            "Specify interface for source address deprecated in SSH connections";
          type string;
        }
        leaf time-out {
          description
            "Specify SSH time-out interval";
          type uint8 {
            range "1..120";
          }
        }
        leaf version {
          description
            "Specify protocol version supported";
          type uint8 {
            range "1..2";
          }
        }
        leaf maxstartups {
          description
            "Maximum number of server sessions";
          type uint8 {
            range "2..128";
          }
        }
        list port {
          description
            "Starting (or only) Port number to listen on";
          key "port-no";
          leaf port-no {
            description
              "Starting Port number";
            type uint16 {
              range "2000..10000";
            }
          }
          leaf low-rotary {
            description
              "Starting (or only) rotary group number";
            type uint8 {
              range "1..127";
            }
          }
          leaf high-rotary {
            description
              "Starting (or only) rotary group number";
            type uint8 {
              range "1..127";
            }
          }
        }
        container bulk-mode {
          description
            "Enable optimizations for bulk data transfer procedures";
          leaf window-size {
            description
              "Window-size value";
            type uint32 {
              range "131072..1073741824";
            }
          }
        }
      }
      container tcp {
        description
          "Global TCP parameters";
        leaf mss {
          description
            "TCP initial maximum segment size";
          type uint16 {
            range "0..10000";
          }
        }
        container path-mtu-discovery {
          description
            "Enable path-MTU discovery on new TCP connections";
          presence "true";
          leaf age-timer {
            description
              "Set PMTU aging timer";
            type union {
              type enumeration {
                enum infinite;
              }
              type uint8 {
                range "10..30";
              }
            }
          }
        }
        leaf selective-ack {
          description
            "Enable TCP selective-ACK";
          type empty;
        }
        leaf synwait-time {
          description
            "Set time to wait on new TCP connections";
          type uint16 {
            range "5..300";
          }
        }
        leaf timestamp {
          description
            "Enable TCP timestamp option";
          type empty;
        }
        leaf window-size {
          description
            "TCP window size";
          type uint32 {
            range "0..1073741823";
          }
        }
      }
      container tftp {
        description
          "tftp configuration commands";
        container boot-interface {
          description
            "Force interface to use for TFTP booting";
          uses ios-ifc:interface-grouping;
        }
        container source-interface {
          description
            "Specify interface for source address in TFTP connections";
          uses ios-ifc:interface-grouping;
        }
        leaf blocksize {
          description
            "Specify TFTP client blocksize";
          type uint16 {
            range "512..8192";
          }
        }
      }
      container access-list {
        description
          "IOS Named access list";
      }
      container device {
        description
          "Device tracking";
      }
      container visibility {
        description
          "NetFlow Global Command";
      }
      container sdwan {
        list route {
          key "vrf ipaddr";
          leaf vrf {
            description
              "Configure ipsec route for a VPN Routing/Forwarding instance";
            must '(/ios:native/ios:vrf/ios:definition[ios:name=current()] and /ios:native/ios:vrf/ios:definition[ios:name=current()]/ios:address-family/ios:ipv4) or /ios:native/ios:ip/ios:vrf[ios:name=current()]' {
              error-message "Please create ipv4 vrf first, and delete the last";
            }
            type string;
          }
          leaf ipaddr {
            description
              "IP address";
            type ios-types:ipv4-address-slash-prefix-len;
          }
          choice tunnel-or-service {
            case tunnel-based {
              container tunnel {
                container active {
                  leaf Tunnel {
                    description
                      "Active tunnel used for SIG";
                    type leafref {
                      path "/ios:native/ios:interface/ios:Tunnel/ios:name";
                    }
                  }
                  container backup {
                    leaf Tunnel {
                      description
                        "Backup tunnel used for SIG";
                      type leafref {
                        path "/ios:native/ios:interface/ios:Tunnel/ios:name";
                      }
                    }
                  }
                }
              }
            }
            case service-based {
              container service {
                choice service-based {
                  case sig-based {
                    leaf sig {
                      type empty;
                    }
                  }
                }
              }
            }
          }
        }
      }
    }
  }

  grouping routes-recurse-grouping {
    leaf route-map {
      description
        "Configure route-map";
      type string;
    }
    leaf multicast {
      description
        "Configure multicast topology";
      type empty;
    }
  }
}
