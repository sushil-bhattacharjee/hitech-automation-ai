module Cisco-IOS-XE-bgp {
  namespace "http://cisco.com/ns/yang/Cisco-IOS-XE-bgp";
  prefix ios-bgp;

  import cisco-semver {
    prefix cisco-semver;
  }
  import ietf-inet-types {
    prefix inet;
  }
  import Cisco-IOS-XE-types {
    prefix ios-types;
  }
  import Cisco-IOS-XE-features {
    prefix ios-features;
  }
  import Cisco-IOS-XE-interface-common {
    prefix ios-ifc;
  }
  import Cisco-IOS-XE-isis {
    prefix ios-isis;
  }
  import Cisco-IOS-XE-ospfv3 {
    prefix ios-ospfv3;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Border Gateway Protocol (BGP) Yang model.
     Copyright (c) 2017-2020 by Cisco Systems, Inc.
     All rights reserved.";

  revision 2021-08-10 {
    description
      "- Must statement and tailf dependency added for neighbor peer-group";
    cisco-semver:module-version "8.0.17060(M)";
  }
  revision 2021-07-01 {
    description
      "- Mark peer-group under template peer-session as obsolete
       - Mark peer-policy under template peer-session inherit as obsolete
       - Deprecate the advertisement-interval ebgp leaf for peer-group
       - Support for BGP redistribution of replicated routes
       - Modified redistribute groupings";
    cisco-semver:module-version "8.0.0";
  }
  revision 2021-03-01 {
    description
      "- Initial revision for 17.5.1
       - Deprecated BGP neighbor long-lived-graceful-restart config
       - Added new grouping for Peer-group Local-as";
    cisco-semver:module-version "7.0.0";
  }
  revision 2020-11-01 {
    description
      "- Update distribute-list config
       - Update inherit peer-policy seq to be mandatory
       - Added bgp large-community support
       - Removed inherit template under peer-group
       - Added inherit peer-policy leaves
       - Update password text config
       - Added support for BGP LU Label Mode
       - Added support for neighbor-additional-paths as choice";
    cisco-semver:module-version "6.0.0";
  }
  revision 2020-07-02 {
    description
      "- Added allow-suppressed";
    cisco-semver:module-version "5.1.0";
  }
  revision 2020-07-01 {
    description
      "- Added propagate-community
       - Updated redistribute nat-route";
    cisco-semver:module-version "5.0.0";
  }
  revision 2020-03-01 {
    description
      "- Added bgp import nhrp
       - Added neighbor accept-route-legacy-rt, inter-as-hybrid,
         long-lived-graceful-restart, and validation config
       - Added stitching-rt support to import config
       - Added bgp rr-group and bgp listen block config
       - Added bgp safe-ebgp-policy config";
    cisco-semver:module-version "4.0.0";
  }
  revision 2019-11-02 {
    description
      "- Update bgp slow-peer and neighbor slow-peer config";
    cisco-semver:module-version "3.0.0";
  }
  revision 2019-11-01 {
    description
      "- Added source paths config
       - Update refresh timers
       - Update advertise and additional-paths config
       - Fixed configuration dependencies
       - Added evpn-limit to address-family advertise config
       - Updated v6 redistribute rip config";
    cisco-semver:module-version "2.0.0";
  }
  revision 2019-07-01 {
    description
      "- Establish semantic version baseline
       - Fix afi-safi containers
       - Add EVPN rewrite-rt
       - Fix or inject-map, recursion host, diverse-path,
         consistency-checker, advertisement-interval and bestpath aigp
       - Update neighbor-path attribute configuration
       - Fixed issues with prefix-length-size, missing-as-worst, and
         prefix-validate
       - Add full template peer-session and peer-policy support, add
         include-connection option for redistribute config, add l2vpn vpls
         suppress-signaling-protocol ldp
       - Edited timers config to prevent invalid values
       - Add ao container and leaves
       - Added multipath-relax option for bgp bestpath as-path
       - Fixed bgp dampening half-life time configuration
       - Fixed redistribute isis delete behavior
       - Fixed issues with bgp nexthop delay";
    cisco-semver:module-version "1.0.0";
  }
  revision 2018-12-11 {
    description
      "fixed get-config issue for template peer-session password";
  }
  revision 2018-12-10 {
    description
      "Fixed as-path to handle regular expression statements";
  }
  revision 2018-11-28 {
    description
      "Fixed default fall-over configuration and fixed network configuration
       under vrf afi-safi";
  }
  revision 2018-11-22 {
    description
      "Cleanup spelling errors in description statements";
  }
  revision 2018-11-20 {
    description
      "fixed as-path ordering issue after replace operation";
  }
  revision 2018-11-15 {
    description
      "Fix CLI ordering for neighbor peer-group and neighbor inherit
       configuration and add vpnv4-unicast peer-group and import configuration";
  }
  revision 2018-11-15 {
    description
      "- Added Support for link-state address family.
       - Added choice for neighbor aigp send-community";
  }
  revision 2018-11-13 {
    description
      "Added presence statement for container ebgp-multihop";
  }
  revision 2018-11-11 {
    description
      "Remove tailf:cli-full-no from redistribute connected and static container";
  }
  revision 2018-11-09 {
    description
      "Fix network config so that network with-mask cannot use the ip address
       class type default mask";
  }
  revision 2018-11-07 {
    description
      "Fixed redistribute isis and redistribute isis area-tag configuration";
  }
  revision 2018-10-19 {
    description
      "Fixed the following:
        - maximum-path under address-family rtfilter
        - removed distance wildbits keyword
        - distribute-list options
        - bgp default local-preference range
        - bgp additional-path options under vpnv4 and vpnv6 address family
        - import l2vpn evpn re-originate stitching-rt
        - long-lived-graceful-restart stale-time
        - neighbor capability container missing under vpnv6 AF
        - remove peer-group under AF vpnv6 unicast
        - snmp context deletion
        - mvpn single-forwarder-selection under address-family ipv4 vrf";
  }
  revision 2018-10-16 {
    description
      "Add 'cli-preformatted' to neighbor password";
  }
  revision 2018-10-15 {
    description
      "Remove vrf leaf from address-family/ipv4/vrf/bgp/router-id.
       Remove extra leafs from address-family/vpnv4/maximum-paths.
       Added choice for address-family/ipv4/vrf/network command.";
  }
  revision 2018-10-14 {
    description
      "Add bgp default inter-as-hybrid advertise-source-routes config";
  }
  revision 2018-10-10 {
    description
      "Rearranged template peer-policy container definition.";
  }
  revision 2018-10-09 {
    description
      "Corrected range for maxas-limit.
       Changed route-map-cache to boolean with default true.";
  }
  revision 2018-10-05 {
    description
      "1. Removed unsupported peer-group option under RTF address-family.
       2. Deleted invalid leaf disable under slow-peer/detection.
       3. Removed unwanted leaves under RTF addr-family maximum-paths.
       4. Added missing leaf under Graceful-restart container.";
  }
  revision 2018-10-04 {
    description
      "Fix for incorrect address-family-maximum-path grouping.
       Added new grouping for evpn address-family additional path configuration.";
  }
  revision 2018-10-03 {
    description
      "Changed the default route-target filter type from string to boolean";
  }
  revision 2018-09-24 {
    description
      "Corrected the BGP peer-group hierarchy under scope mode";
  }
  revision 2018-09-14 {
    description
      "Fixed table-map config container";
  }
  revision 2018-08-31 {
    description
      "add delete annotations for AF neighbor configurations";
  }
  revision 2018-08-04 {
    description
      "bgp advertisement-interval not getting configured through netconf. Update neighbor ebgp-multihop and next-hop-unchanged dependencies";
  }
  revision 2018-08-02 {
    description
      "Add default values to leaves";
  }
  revision 2018-08-01 {
    description
      "Fixed order of as-path access-list";
  }
  revision 2018-07-30 {
    description
      "Update config annotations for address-family, redistribute, and fall-over commands";
  }
  revision 2018-07-18 {
    description
      "Fixed next-hop-self, fall-over bfd, as-override, allowas-in";
  }
  revision 2018-07-16 {
    description
      "Fix neighbor remote-as and peer-group config";
  }
  revision 2018-07-06 {
    description
      "Edit neighbors timer container to allow for no timer config";
  }
  revision 2018-06-28 {
    description
      "Fix for router-id vrf value, vrf neighbor configuration,
       address-family deletion, and remove vrf auto-summary";
  }
  revision 2018-06-28 {
    description
      "added must constraints for deleting vrf";
  }
  revision 2018-06-25 {
    description
      "fix bgp timers";
  }
  revision 2018-06-08 {
    description
      "Create new groupings for global, af, and neighbor scopes in order to
       remove invalid leaves present in model";
  }
  revision 2018-06-07 {
    description
      "Added bgp router-id interface";
  }
  revision 2018-05-21 {
    description
      "change redistribute router id to type leafref under router bgp address-family";
  }
  revision 2018-05-15 {
    description
      "fix send-community, fall-over, redistribute, max-paths, backdoor,
       log-neighbor-changes, and network/mask errors";
  }
  revision 2018-05-01 {
    description
      "restructure BGP neighbor and peer-group";
  }
  revision 2018-05-01 {
    description
      "Restrict propagate-aspath to 'address-family <ipv4/ipv6> vrf <id>'";
  }
  revision 2018-04-19 {
    description
      "Add support for propagate-as-path in address-family's ipv4 & ipv6";
  }
  revision 2018-04-02 {
    description
      "Some more Evpn cli added";
  }
  revision 2018-03-15 {
    description
      "Evpn cli for bgp added";
  }
  revision 2018-02-01 {
    description
      "support multiple aggregate-address for both ipv4 and ipv6";
  }
  revision 2018-01-26 {
    description
      "fix config issue -redistribute OSPF under bgp process";
  }
  revision 2018-01-10 {
    description
      "fix bgp best path med missing-as-worst";
  }
  revision 2017-12-11 {
    description
      "Add support for redistribute nat-route dia/outside";
  }
  revision 2017-11-09 {
    description
      "fix aggregate-address cli generation issue";
  }
  revision 2017-10-10 {
    description
      "Add redistribute omp support";
  }
  revision 2017-09-18 {
    description
      "BGP neighbor should match a v4/v6 address";
  }
  revision 2017-09-08 {
    description
      "Add show no for enhanced-error";
  }
  revision 2017-08-17 {
    description
      "send-community delete before change";
  }
  revision 2017-08-10 {
    description
      "Add bgp mpls-local-label, import path selection all, bgp best path as-path ignore";
  }
  revision 2017-08-02 {
    description
      "Fix delete for redistribute connected";
  }
  revision 2017-07-30 {
    description
      "adding neighbor remove-private-as support";
  }
  revision 2017-07-27 {
    description
      "Fix delete for redistribute connected";
  }
  revision 2017-07-17 {
    description
      "adding neighbor send-label";
  }
  revision 2017-07-10 {
    description
      "adding redistribute ospfv3";
  }
  revision 2017-05-25 {
    description
      "adding neighbor listen and next-hop-self all";
  }
  revision 2017-04-28 {
    description
      "inet:ipv6-prefix changed to ios-types:ipv6-prefix";
  }
  revision 2017-03-02 {
    description
      "NED extension - add version4 for bgp template peer-session";
  }
  revision 2017-02-08 {
    description
      "NED extension - router bgp address-family options -
                   soo, max paths, import path";
  }
  revision 2017-02-07 {
    description
      "Initial revision";
  }

  grouping bgp-router-id-grouping {
    container router-id {
      description
        "Override configured router identifier (peers will reset)";
      choice id-choice {
        leaf ip-id {
          description
            "Manually configured router identifier";
          type inet:ipv4-address;
        }
        container interface {
          description
            "Use IPv4 address on interface";
          uses ios-ifc:interface-grouping;
        }
        leaf vrf {
          description
            "vrf-specific router id configuration";
          type enumeration {
            enum auto-assign;
          }
        }
      }
    }
  }

  grouping bgp-vrf-router-id-grouping {
    container router-id {
      description
        "Override configured router identifier (peers will reset)";
      choice id-choice {
        leaf ip-id {
          description
            "Manually configured router identifier";
          type inet:ipv4-address;
        }
        container interface {
          description
            "Use IPv4 address on interface";
          uses ios-ifc:interface-grouping;
        }
        leaf auto-assign {
          description
            "Automatically assign bgp router id";
          type empty;
        }
      }
    }
  }

  grouping global-bgp-grouping {
    description
      "BGP specific commands";
    leaf aigp-rib-metric {
      description
        "Install RIB metric as NH metric + metric on AIGP attribute";
      type empty;
    }
    leaf always-compare-med {
      description
        "Allow comparing MED from different neighbors";
      type empty;
    }
    container asnotation {
      description
        "Change the default AS plain notation";
      leaf dot {
        description
          "AS dot notation";
        type empty;
      }
    }
    container bestpath {
      description
        "Change the default best path selection";
      leaf as-path {
        description
          "Ignore the as-path in bestpath selection";
        type enumeration {
          enum ignore;
          enum multipath-relax;
        }
      }
      leaf aigp {
        description
          "if both paths does not have aigp ignore on bestpath comparison";
        type enumeration {
          enum ignore;
        }
      }
      leaf compare-routerid {
        type empty;
      }
      container cost-community {
        description
          "cost community";
        leaf ignore {
          description
            "Ignore cost communities in best path selection";
          type empty;
        }
      }
      container igp-metric {
        status obsolete;
        description
          "igp metric (OBSOLETE)";
        leaf ignore {
          status obsolete;
          description
            "Ignore igp metric in best path selection";
          type empty;
        }
      }
      container med {
        description
          "MED attribute";
        leaf confed-leaf {
          description
            "Compare MED among confederation paths";
          type empty;
        }
        leaf missing-as-worst-leaf {
          description
            "Treat missing MED as the least preferred one";
          type empty;
        }
        choice med-choice {
          status obsolete;
          container confed {
            status obsolete;
            description
              "Compare MED among confederation paths (OBSOLETE) - Please use
               med/confed-leaf instead";
            presence "Compare MED among confederation paths";
            leaf missing-as-worst {
              status obsolete;
              description
                "Treat missing MED as the least preferred one (OBSOLETE) -
                 Please use med/missing-as-worst-leaf instead";
              type empty;
            }
          }
          leaf missing-as-worst {
            status obsolete;
            description
              "Treat missing MED as the least preferred one (OBSOLETE) - Please
               us med/missing-as-worst-leaf instead";
            type empty;
          }
        }
      }
    }
    container client-to-client {
      description
        "Configure client to client route reflection";
      leaf reflection {
        description
          "reflection of routes allowed";
        type boolean;
      }
    }
    leaf cluster-id {
      type union {
        type uint32 {
          range "1..4294967294";
        }
        type inet:ipv4-address;
      }
    }
    container confederation {
      description
        "AS confederation parameters";
      leaf identifier {
        type inet:as-number;
      }
      container peers {
        description
          "Peer ASs in BGP confederation";
        leaf-list peers-as {
          type inet:as-number;
        }
      }
    }
    container consistency-checker {
      description
        "Consistency-checker";
      container auto-repair {
        description
          "Auto-Repair";
        presence "true";
        leaf interval {
          description
            "Interval (minutes)";
          default "1440";
          type uint16 {
            range "5..1440";
          }
        }
      }
      container error-message {
        description
          "error-message";
        presence "true";
        leaf interval {
          description
            "Interval (minutes)";
          type uint16 {
            range "5..1440";
          }
        }
      }
      must "(not(auto-repair) and not(error-message)) or (auto-repair
            and not(error-message)) or (not(auto-repair) and error-message)" {
        error-message
          "error-message and auto-repair cannot be configured at
           the same time";
      }
    }
    container default {
      description
        "Configure BGP defaults";
      container inter-as-hybrid {
        description
          "Configure Inter-AS Hybrid peer defaults";
        leaf advertise-source-routes {
          description
            "Advertise non-imported routes to hybrid peers";
          type boolean;
        }
      }
      leaf ipv4-unicast {
        description
          "Activate ipv4-unicast for a peer by default";
        default "true";
        type boolean;
      }
      leaf ipv6-nexthop {
        description
          "Default IPv6 nexthop format";
        default "true";
        type boolean;
      }
      leaf local-preference {
        description
          "local preference (higher=more preferred)";
        default "100";
        type uint32 {
          range "0..4294967295";
        }
      }
      container route-target {
        description
          "Control behavior based on Route-Target attributes";
        leaf filter {
          description
            "Default route-target filter";
          default "true";
          type boolean;
        }
      }
    }
    leaf deterministic-med {
      description
        "Pick the best-MED path among paths advertised from the neighboring AS";
      type empty;
    }
    container dynamic-med-interval {
      description
        "Set the interval to re-compute dynamic MED from IGP metric";
      leaf interval {
        description
          "Interval value (seconds)";
        default "600";
        type uint32 {
          range "60..4294967295";
        }
      }
    }
    leaf enforce-first-as-boolean {
      description
        "Enforce the first AS for EBGP routes(default)";
      default "true";
      type boolean;
    }
    leaf enforce-first-as {
      status obsolete;
      description
        "Enforce the first AS for EBGP routes(OBSOLETE) - Please us
         enforce-first-as-boolean instead.";
      type empty;
    }
    leaf enhanced-error {
      description
        "Enabled BGP Enhanced error handling";
      type boolean;
    }
    leaf fast-external-fallover {
      description
        "Immediately reset session if a link to a directly connected external peer goes down";
      type boolean;
    }
    container graceful-restart {
      description
        "Graceful restart capability parameters";
      presence "Graceful restart capability parameters";
      leaf all {
        description
          "Enable BGP GR for all platforms (even non-NSF capable ones)";
        type empty;
      }
      leaf extended {
        description
          "Enable Graceful-Restart Extension";
        type empty;
      }
      leaf restart-time {
        description
          "Set the max time needed to restart and come back up";
        default "120";
        type uint16 {
          range "1..3600";
        }
      }
      leaf stalepath-time {
        description
          "Set the max time to hold onto restarting peer's stale paths";
        default "360";
        type uint16 {
          range "1..3600";
        }
      }
    }
    container ha-mode {
      description
        "Select BGP High Availability mode";
      container sso {
        description
          "BGP High Availability NSR sso mode";
        presence "true";
        leaf prefer {
          description
            "Prefer BGP High Availability NSR sso mode";
          type empty;
        }
      }
    }
    container listen {
      description
        "Neighbor subnet range listener";
      leaf limit {
        description
          "Set the max limit for the dynamic subnet range neighbors";
        default "100";
        type uint16 {
          range "1..10000";
        }
      }
      list range {
        description
          "Subnet network range";
        key "network-range peer-group";
        leaf network-range {
          type union {
            type inet:ipv4-prefix;
            type ios-types:ipv6-prefix;
          }
        }
        leaf peer-group {
          description
            "Member of the peer-group";
          type string;
        }
      }
      list block {
        description
          "block address for dynamic peering";
        key "peering-address";
        leaf peering-address {
          type union {
            type inet:ipv4-address;
            type inet:ipv6-address;
          }
        }
      }
    }
    leaf log-neighbor-changes {
      description
        "Log neighbor up/down and reset reason";
      default "true";
      type boolean;
    }
    leaf maxas-limit {
      description
        "Allow AS-PATH attribute from any neighbor imposing a limit on number of ASes";
      type uint16 {
        range "1..254";
      }
    }
    leaf maxcommunity-limit {
      description
        "Number of communities in the COMMUNITY attribute";
      type uint16 {
        range "1..1018";
      }
    }
    container maxextcommunity-limit {
      description
        "Allow EXTENDED COMMUNITY attribute from any neighbor imposing a
         limit on number of extended communities";
      leaf number {
        description
          "Number of extended communities in the EXTENDED COMMUNITY
           attribute";
        type uint16 {
          range "1..509";
        }
      }
    }
    leaf maxlargecommunity-limit {
      description
        "Number of large communities in the LARGE COMMUNITY attribute";
      type uint16 {
        range "1..339";
      }
    }
    container nopeerup-delay {
      description
        "Set how long BGP will wait for the first peer to come up before beginning the update delay or graceful restart timers (in seconds)";
      leaf cold-boot {
        description
          "Delay in seconds";
        type uint16 {
          range "1..3600";
        }
      }
      leaf nsf-switchover {
        description
          "Delay in seconds";
        type uint16 {
          range "1..3600";
        }
      }
      leaf post-boot {
        description
          "Delay in seconds";
        type uint16 {
          range "1..3600";
        }
      }
      leaf user-initiated {
        description
          "Delay in seconds";
        type uint16 {
          range "1..3600";
        }
      }
    }
    container refresh {
      description
        "refresh";
      container max-eor-time {
        description
          "Configure refresh max-eor time";
        leaf refresh-disable {
          status obsolete;
          default "0";
          type enumeration {
            enum 0;
          }
        }
        leaf timer-interval {
          default "0";
          type uint16 {
            range "0 | 600..3600";
          }
        }
      }
      container stalepath-time {
        description
          "Configure refresh stale-path time";
        leaf refresh-disable {
          status obsolete;
          default "0";
          type enumeration {
            enum 0;
          }
        }
        leaf timer-interval {
          default "0";
          type uint16 {
            range "0 | 600..3600";
          }
        }
      }
    }
    container regexp {
      description
        "Select regular expression engine";
      leaf deterministic {
        description
          "Enable bounded-execution-time regular expression engine";
        default "true";
        type boolean;
      }
    }
    leaf route-map-cache {
      description
        "Enable route-map caching";
      default "true";
      type boolean;
    }
    uses bgp-router-id-grouping;
    leaf safe-ebgp-policy {
      description
        " Allow propagation of ebgp routes only with policy configured. Command may trigger refresh on all sessions!";
      type empty;
    }
    container sso {
      description
        "Stateful Switchover";
      leaf route-refresh-enable {
        description
          "Enable SSO only for Route-Refresh capable peers";
        type empty;
      }
    }
    container transport {
      description
        "Transport options";
      leaf path-mtu-discovery {
        description
          "Use transport path MTU discovery";
        default "true";
        type boolean;
      }
    }
    leaf update-delay {
      description
        "Set the max initial delay for sending update";
      default "120";
      type uint16 {
        range "1..3600";
      }
    }
  }

  grouping bgp-additional-paths-grouping {
    container additional-paths {
      description
        "Additional paths in the BGP table";
      leaf install {
        description
          "Additional paths to install into RIB";
        type empty;
      }
      leaf receive {
        description
          "Receive additional paths from neighbors";
        type empty;
      }
      container select {
        description
          "Selection criteria to pick the paths";
        container all-best {
          description
            "Select all, group-best, best available paths";
          leaf all {
            description
              "Select all, group-best, best available paths";
            type empty;
          }
          leaf group-best {
            description
              "Select group-best path";
            type empty;
          }
          leaf best {
            description
              "Number of best paths in additional paths to be selected";
            type uint8 {
              range "2..3";
            }
          }
        }
        container best-external-backup {
          description
            "Select best-external and backup path";
          leaf best-external {
            description
              "Select best-external path";
            type empty;
          }
          leaf backup {
            description
              "Select backup path";
            type empty;
          }
        }
      }
      container send {
        description
          "Send additional paths to neighbors";
        presence "true";
        leaf receive {
          description
            "Receive additional paths from neighbors";
          type empty;
        }
      }
    }
  }

  grouping bgp-evpn-additional-paths-grouping {
    container additional-paths {
      description
        "Additional paths in the BGP table";
      leaf receive {
        description
          "Receive additional paths from neighbors";
        type empty;
      }
      container select {
        description
          "Selection criteria to pick the paths";
        leaf all {
          description
            "Select all available paths";
          type empty;
        }
        leaf group-best {
          description
            "Select group-best path";
          type empty;
        }
        leaf best {
          description
            "Number of best paths in additional paths to be selected";
          type uint8 {
            range "2..3";
          }
        }
      }
      container send {
        description
          "Send additional paths to neighbors";
        presence "true";
        leaf receive {
          description
            "Receive additional paths from neighbors";
          type empty;
        }
      }
    }
  }

  grouping bgp-additional-paths-vpn-grouping {
    container additional-paths {
      description
        "Additional paths in the BGP table";
      leaf install {
        description
          "Additional paths to install into RIB";
        type empty;
      }
      container select {
        description
          "Selection criteria to pick the paths";
        leaf best-external {
          description
            "Select best-external path";
          type empty;
        }
        leaf backup {
          description
            "Select backup path";
          type empty;
        }
      }
    }
  }

  grouping bgp-vrf-additional-paths-grouping {
    container additional-paths {
      description
        "Additional paths in the BGP table";
      leaf install {
        description
          "Additional paths to install into RIB";
        type empty;
      }
      leaf receive {
        status obsolete;
        description
          "Receive additional paths from neighbors (OBSOLETE)";
        type empty;
      }
      container select {
        description
          "Selection criteria to pick the paths";
        container all-best {
          status obsolete;
          description
            "Select all, group-best, best available paths (OBSOLETE)";
          leaf all {
            status obsolete;
            description
              "Select all, group-best, best available paths (OBSOLETE)";
            type empty;
          }
          leaf group-best {
            status obsolete;
            description
              "Select group-best path (OBSOLETE)";
            type empty;
          }
          leaf best {
            status obsolete;
            description
              "Number of best paths in additional paths to be selected (OBSOLETE)";
            type uint8 {
              range "2..3";
            }
          }
        }
        container best-external-backup {
          description
            "Select best-external and backup path";
          leaf best-external {
            description
              "Select best-external path";
            type empty;
          }
          leaf backup {
            description
              "Select backup path";
            type empty;
          }
        }
      }
      container send {
        status obsolete;
        description
          "Send additional paths to neighbors (OBSOLETE)";
        presence "true";
        leaf receive {
          status obsolete;
          description
            "Receive additional paths from neighbors (OBSOLETE)";
          type empty;
        }
      }
    }
  }

  grouping bgp-advertise-best-external-grouping {
    leaf advertise-best-external {
      description
        "Advertise best external path to internal peers";
      type empty;
    }
  }

  grouping bgp-aggregate-timer-grouping {
    container aggregate-timer {
      description
        "Configure aggregation timer";
      choice timer-choice {
        leaf aggregate-timer {
          description
            "Timer interval";
          default "40";
          type uint8 {
            range "6..60";
          }
        }
        leaf disable-timer {
          description
            "Timer interval";
          type enumeration {
            enum 0;
          }
        }
      }
    }
  }

  grouping bgp-bestpath-grouping {
    container bestpath {
      description
        "Change the default best path selection";
      container igp-metric {
        description
          "igp metric";
        leaf ignore {
          description
            "Ignore igp metric in best path selection";
          type empty;
        }
      }
      container prefix-validate {
        description
          "Prefix origin validation";
        leaf allow-invalid {
          description
            "Allow invalid routes to be considered for best path";
          type empty;
        }
        leaf disable {
          description
            "Disable prefix validation";
          type empty;
        }
      }
    }
  }

  grouping bgp-bestpath-without-validation-grouping {
    container bestpath {
      description
        "Change the default best path selection";
      container igp-metric {
        description
          "igp metric";
        leaf ignore {
          description
            "Ignore igp metric in bestpath selection";
          type empty;
        }
      }
      container prefix-validate {
        status obsolete;
        description
          "Prefix origin validation (OBSOLETE)";
        leaf allow-invalid {
          status obsolete;
          description
            "Allow invalid routes to be considered for best path (OBSOLETE)";
          type empty;
        }
        leaf disable {
          status obsolete;
          description
            "Disable prefix validation (OBSOLETE)";
          type empty;
        }
      }
    }
  }

  grouping bgp-dampening-grouping {
    container dampening {
      description
        "Enable route-flap dampening";
      presence "enable bgp route-flap dampening";
      choice dampening-choice {
        leaf route-map {
          description
            "Route-map to specify criteria for dampening";
          type string;
        }
        container dampen {
          leaf half-life-time {
            description
              "Half-life time for the penalty";
            type uint8 {
              range "1 .. 45";
            }
          }
          leaf reuse-time {
            description
              "Value to start reusing a route";
            type uint16 {
              range "1 .. 20000";
            }
          }
          leaf suppress-time {
            description
              "Value to start suppressing a route";
            must '. >= ../reuse-time' {
              error-message "suppress-time should be greater than reuse-time";
            }
            type uint16 {
              range "1 .. 20000";
            }
          }
          leaf max-suppress-time {
            description
              "Maximum duration to suppress a stable route";
            must '. >= ../half-life-time' {
              error-message "max-suppress-time should be greater than half-life-time";
            }
            type uint8 {
              range "1 .. 255";
            }
          }
          must '((half-life-time) and (reuse-time) and (suppress-time) and (max-suppress-time)) or ((half-life-time) and not(reuse-time) and not(suppress-time) and not(reuse-time))' {
            error-message "must configure (half-life-time) or (half-life-time,reuse-time,suppress-time and max-suppress-time)";
          }
        }
      }
    }
  }

  grouping bgp-default-grouping {
    container route-target {
      description
        "Control behavior based on Route-Target attributes";
      leaf filter {
        description
          "Default route-target filter";
        default "true";
        type boolean;
      }
    }
  }

  grouping bgp-dmzlink-bw-grouping {
    leaf dmzlink-bw {
      description
        "Use DMZ Link Bandwidth as weight for BGP multipaths";
      type empty;
    }
  }

  grouping bgp-inject-map-grouping {
    list inject-map {
      description
        "Route map which specifies prefixes to inject";
      key "name";
      leaf name {
        type string;
      }
      leaf exist-map {
        description
          "Route map which specifies exist condition";
        type string;
        mandatory true;
      }
      leaf copy-attributes {
        description
          "Copy attributes from aggregate";
        type empty;
      }
    }
  }

  grouping bgp-listen-vrf-grouping {
    container listen {
      description
        "Neighbor subnet range listener";
      leaf limit {
        description
          "Set the max limit for the dynamic subnet range neighbors in vrf";
        default "100";
        type uint16 {
          range "1..10000";
        }
      }
      list block {
        description
          "block address for dynamic peering";
        key "peering-address";
        leaf peering-address {
          type union {
            type inet:ipv4-address;
            type inet:ipv6-address;
          }
        }
      }
    }
  }

  grouping bgp-nexthop-grouping {
    container nexthop {
      description
        "Nexthop tracking commands";
      container trigger {
        description
          "Nexthop triggering";
        leaf delay {
          description
            "Set the delay to trigger nexthop tracking";
          default "5";
          when "../enable = 'true'";
          type uint8 {
            range "0..100";
          }
        }
        leaf enable {
          description
            "Enable nexthop tracking";
          default "true";
          type boolean;
        }
      }
      leaf route-map {
        description
          "Route map for valid nexthops";
        type string;
      }
    }
  }

  grouping bgp-recursion-grouping {
    container recursion {
      description
        "recursion rule for the nexthops";
      leaf host {
        description
          "recursion via host for the nexthops";
        type empty;
      }
    }
  }

  grouping bgp-redistribute-internal-grouping {
    leaf redistribute-internal {
      description
        "Allow redistribution of iBGP into IGPs (dangerous)";
      type empty;
    }
  }

  grouping bgp-redistribute-internal-obsolete-grouping {
    leaf redistribute-internal {
      description
        "Allow redistribution of iBGP into IGPs (dangerous) (OBSOLETE) - This
         configuration is no longer valid at this location";
      status obsolete;
      type empty;
    }
  }

  grouping bgp-route-map-grouping {
    container route-map {
      description
        "bgp route-map commands";
      leaf priority {
        description
          "Have route-map set commands take priority over BGP commands such as
           next-hop-unchanged";
        type empty;
      }
    }
  }

  grouping bgp-rr-group-grouping {
    leaf rr-group {
      description
        "Partition the network by forming RR groups";
      type string;
    }
  }

  grouping bgp-scan-time-grouping {
    leaf scan-time {
      description
        "Configure background scanner interval";
      default "60";
      type uint8 {
        range "5..60";
      }
    }
  }

  grouping bgp-slow-peer-grouping {
    container slow-peer {
      description
        "Configure slow-peer";
      container detection {
        description
          "Slow-peer detection";
        presence "true";
        leaf threshold {
          description
            "Threshold value (seconds)";
          default "300";
          type uint16 {
            range "120..3600";
          }
        }
        leaf disable {
          status obsolete;
          description
            "Disable slow-peer detection";
          type empty;
        }
      }
      container split-update-group {
        description
          "Configure slow-peer split-update-group";
        container dynamic {
          description
            "Dynamically split the slow peer to slow-update group";
          presence "true";
          leaf permanent {
            description
              "Keep the slow-peer permanently in slow-update group";
            type empty;
          }
          leaf disable {
            status obsolete;
            description
              "Disable slow-peer detection";
            type empty;
          }
        }
        leaf static {
          status obsolete;
          description
            "Static slow-peer";
          type empty;
        }
      }
    }
  }

  grouping bgp-soft-reconfig-backup-grouping {
    leaf soft-reconfig-backup {
      description
        "Use soft-reconfiguration inbound only when route-refresh is not negotiated";
      type empty;
    }
  }

  grouping bgp-sourced-paths-grouping {
    container sourced-paths {
      description
        "Allow sourcing of multiple paths per protocol";
      container per-net {
        description
          "Allow per-network sourcing of multiple paths";
        container isis {
          description
            "Allow sourcing of multiple paths from isis";
          leaf all {
            description
              "Allow sourcing of all sourced paths as in rib";
            type empty;
          }
        }
        container ospf {
          description
            "Allow sourcing of multiple paths from ospf";
          leaf all {
            description
              "Allow sourcing of all sourced paths as in rib";
            type empty;
          }
        }
        container ospfv3 {
          description
            "Allow sourcing of multiple paths from ospfv3";
          leaf all {
            description
              "Allow sourcing of all sourced paths as in rib";
            type empty;
          }
        }
        container static {
          description
            "Allow sourcing of multiple paths from static";
          leaf all {
            description
              "Allow sourcing of all sourced paths as in rib";
            type empty;
          }
        }
      }
    }
  }

  grouping bgp-suppress-inactive-grouping {
    leaf suppress-inactive {
      description
        "Suppress routes that are not in the routing table";
      type empty;
    }
  }

  grouping bgp-update-group-grouping {
    container update-group {
      description
        "Manage peers in bgp update groups";
      container split {
        description
          "Split update groups based on Policy";
        leaf as-override {
          description
            "Keep peers with as-override in different update groups";
          type empty;
        }
      }
    }
  }

  grouping neighbor-accept-route-legacy-rt-grouping {
    leaf accept-route-legacy-rt {
      description
        "Accept Legacy Route Target";
      type empty;
    }
  }

  grouping neighbor-activate-grouping {
    leaf activate {
      description
        "Enable the address family for this neighbor";
      type empty;
    }
  }

  grouping neighbor-additional-paths-grouping {
    container additional-paths {
      choice additional-paths-choice {
        leaf disable-paths {
          description
            "Disable additional paths for this neighbor";
          type empty;
        }
        leaf receive-paths {
          description
            "Receive additional paths from neighbors";
          type empty;
        }
        container send-paths {
          description
            "Send additional paths to this neighbor";
          presence "true";
          leaf receive {
            description
              "Receive additional paths from this neighbor";
            type empty;
          }
        }
      }
      leaf disable {
        description
          "Disable additional paths for this neighbor";
        status deprecated;
        type empty;
      }
      leaf receive {
        description
          "Receive additional paths from neighbors";
        status deprecated;
        type empty;
      }
      container send {
        description
          "Send additional paths to this neighbor";
        status deprecated;
        presence "true";
        leaf receive {
          description
            "Receive additional paths from this neighbor";
          status deprecated;
          type empty;
        }
      }
    }
  }

  grouping neighbor-advertise-grouping {
    container advertise {
      description
        "Advertise to this neighbor";
      choice advertise-choice {
        container additional-paths-choice {
          description
            "Advertise additional paths";
          leaf all {
            description
              "Select all, group-best, best available paths";
            type empty;
          }
          leaf group-best {
            description
              "Select group-best path";
            type empty;
          }
          leaf best {
            description
              "Number of best paths in additional paths to be selected";
            type uint8 {
              range "2..3";
            }
          }
        }
        container diverse-path-choice {
          description
            "Advertise diverse path";
          leaf backup {
            description
              "Diverse path can be backup path";
            type empty;
          }
          leaf mpath {
            description
              "Diverse path can be multipath";
            type empty;
          }
          must '(../../ios-bgp:route-reflector-client and (backup or mpath)) or (not(backup) and not(mpath))' {
            error-message "Neighbor must be route reflector client in order to configure diverse-path";
          }
        }
      }
      container additional-paths {
        status obsolete;
        description
          "Advertise additional paths (OBSOLETE)";
        container all {
          status obsolete;
          description
            "Select all available paths (OBSOLETE)";
          presence "true";
          container best {
            status obsolete;
            description
              "Select best N paths (OBSOLETE)";
            list best-range {
              status obsolete;
              key "range";
              leaf range {
                status obsolete;
                description
                  "Number of best paths in additional paths to be selected (OBSOLETE)";
                type uint8 {
                  range "2..3";
                }
              }
              leaf group-best {
                status obsolete;
                description
                  "Select group-best paths (OBSOLETE)";
                type empty;
              }
            }
          }
          container group-best {
            status obsolete;
            description
              "Select group-best paths (OBSOLETE)";
            presence "true";
            leaf best {
              status obsolete;
              description
                "Number of best paths in additional paths to be selected (OBSOLETE)";
              type uint8 {
                range "2..3";
              }
            }
          }
        }
        container best {
          status obsolete;
          description
            "Select best N paths (OBSOLETE)";
          list best-range {
            status obsolete;
            key "range";
            leaf range {
              status obsolete;
              description
                "Number of best paths in additional paths to be selected (OBSOLETE)";
              type uint8 {
                range "2..3";
              }
            }
            leaf all {
              status obsolete;
              description
                "Select all available paths (OBSOLETE)";
              type empty;
            }
            container group-best {
              status obsolete;
              description
                "Select group-best paths (OBSOLETE)";
              presence "true";
              leaf all {
                status obsolete;
                description
                  "Select all available paths (OBSOLETE)";
                type empty;
              }
            }
          }
        }
        container group-best {
          status obsolete;
          description
            "Select group-best paths (OBSOLETE)";
          presence "true";
          leaf all {
            status obsolete;
            description
              "Select all available paths (OBSOLETE)";
            type empty;
          }
          leaf best {
            status obsolete;
            description
              "Number of best paths in additional paths to be selected (OBSOLETE)";
            type uint8 {
              range "2..3";
            }
          }
        }
      }
      leaf best-external {
        description
          "Advertise best-external (at RRs best-internal) path";
        type empty;
      }
      container diverse-path {
        status obsolete;
        description
          "Advertise diverse path (OBSOLETE)";
        container backup {
          status obsolete;
          description
            "Diverse path can be backup path (OBSOLETE)";
          presence "true";
          leaf mpath {
            status obsolete;
            description
              "Diverse path can be multipath (OBSOLETE)";
            type empty;
          }
        }
        leaf mpath {
          status obsolete;
          description
            "Diverse path can be multipath (OBSOLETE)";
          type empty;
        }
        must '(../../ios-bgp:route-reflector-client and (backup or mpath)) or (not(backup) and not(mpath))' {
          error-message "Neighbor must be route reflector client in order to configure diverse-path";
        }
      }
    }
  }

  grouping evpn-neighbor-advertise-grouping {
    container advertise {
      description
        "Advertise to this neighbor";
      container additional-paths {
        description
          "Advertise additional paths";
        container all-best {
          description
            "Select all, group-best, best available paths";
          leaf all {
            description
              "Select all, group-best, best available paths";
            type empty;
          }
          leaf group-best {
            description
              "Select group-best path";
            type empty;
          }
          leaf best {
            description
              "Number of best paths in additional paths to be selected";
            type uint8 {
              range "2..3";
            }
          }
        }
        container all {
          status obsolete;
          description
            "Select all available paths (OBSOLETE)";
          presence "true";
          container best {
            status obsolete;
            description
              "Select best N paths (OBSOLETE)";
            list best-range {
              status obsolete;
              key "range";
              leaf range {
                status obsolete;
                description
                  "Number of best paths in additional paths to be selected (OBSOLETE)";
                type uint8 {
                  range "2..3";
                }
              }
              leaf group-best {
                status obsolete;
                description
                  "Select group-best paths (OBSOLETE)";
                type empty;
              }
            }
          }
          container group-best {
            status obsolete;
            description
              "Select group-best paths (OBSOLETE)";
            presence "true";
            leaf best {
              status obsolete;
              description
                "Number of best paths in additional paths to be selected (OBSOLETE)";
              type uint8 {
                range "2..3";
              }
            }
          }
        }
        container best {
          status obsolete;
          description
            "Select best N paths (OBSOLETE)";
          list best-range {
            status obsolete;
            key "range";
            leaf range {
              status obsolete;
              description
                "Number of best paths in additional paths to be selected (OBSOLETE)";
              type uint8 {
                range "2..3";
              }
            }
            leaf all {
              status obsolete;
              description
                "Select all available paths (OBSOLETE)";
              type empty;
            }
            container group-best {
              status obsolete;
              description
                "Select group-best paths (OBSOLETE)";
              presence "true";
              leaf all {
                status obsolete;
                description
                  "Select all available paths (OBSOLETE)";
                type empty;
              }
            }
          }
        }
        container group-best {
          status obsolete;
          description
            "Select group-best paths (OBSOLETE)";
          presence "true";
          leaf all {
            status obsolete;
            description
              "Select all available paths (OBSOLETE)";
            type empty;
          }
          leaf best {
            status obsolete;
            description
              "Number of best paths in additional paths to be selected (OBSOLETE)";
            type uint8 {
              range "2..3";
            }
          }
        }
      }
      leaf best-external {
        status obsolete;
        description
          "Advertise best-external (at RRs best-internal) path (OBSOLETE)";
        type empty;
      }
      container diverse-path {
        status obsolete;
        description
          "Advertise diverse path (OBSOLETE)";
        container backup {
          status obsolete;
          description
            "Diverse path can be backup path (OBSOLETE)";
          presence "true";
          leaf mpath {
            status obsolete;
            description
              "Diverse path can be multipath (OBSOLETE)";
            type empty;
          }
        }
        leaf mpath {
          status obsolete;
          description
            "Diverse path can be multipath (OBSOLETE)";
          type empty;
        }
      }
    }
  }

  grouping neighbor-vpn-advertise-grouping {
    container advertise {
      description
        "Advertise to this neighbor";
      container additional-paths {
        status obsolete;
        description
          "Advertise additional paths";
        container all {
          status obsolete;
          description
            "Select all available paths";
          presence "true";
          container best {
            status obsolete;
            description
              "Select best N paths";
            list best-range {
              status obsolete;
              key "range";
              leaf range {
                status obsolete;
                description
                  "Number of best paths in additional paths to be selected";
                type uint8 {
                  range "2..3";
                }
              }
              leaf group-best {
                status obsolete;
                description
                  "Select group-best paths";
                type empty;
              }
            }
          }
          container group-best {
            status obsolete;
            description
              "Select group-best paths";
            presence "true";
            leaf best {
              status obsolete;
              description
                "Number of best paths in additional paths to be selected";
              type uint8 {
                range "2..3";
              }
            }
          }
        }
        container best {
          status obsolete;
          description
            "Select best N paths";
          list best-range {
            status obsolete;
            key "range";
            leaf range {
              status obsolete;
              description
                "Number of best paths in additional paths to be selected";
              type uint8 {
                range "2..3";
              }
            }
            leaf all {
              status obsolete;
              description
                "Select all available paths";
              type empty;
            }
            container group-best {
              status obsolete;
              description
                "Select group-best paths";
              presence "true";
              leaf all {
                status obsolete;
                description
                  "Select all available paths";
                type empty;
              }
            }
          }
        }
        container group-best {
          status obsolete;
          description
            "Select group-best paths";
          presence "true";
          leaf all {
            status obsolete;
            description
              "Select all available paths";
            type empty;
          }
          leaf best {
            status obsolete;
            description
              "Number of best paths in additional paths to be selected";
            type uint8 {
              range "2..3";
            }
          }
        }
      }
      leaf best-external {
        description
          "Advertise best-external (at RRs best-internal) path";
        type empty;
      }
      container diverse-path {
        description
          "Advertise diverse path";
        leaf backup-path {
          description
            "Diverse path can be backup path";
          when '../../../route-reflector-client';
          type empty;
        }
        container backup {
          status obsolete;
          description
            "Diverse path can be backup path";
          presence "true";
          leaf mpath {
            status obsolete;
            description
              "Diverse path can be multipath";
            type empty;
          }
        }
        leaf mpath {
          description
            "Diverse path can be multipath";
          when '../../../route-reflector-client';
          type empty;
        }
      }
    }
  }

  grouping neighbor-advertise-map-grouping {
    container advertise-map {
      description
        "specify route-map for conditional advertisement";
      list name {
        key "word";
        leaf word {
          description
            "advertise route-map name";
          type string;
        }
        leaf-list exist-map-list {
          description
            "condition route-map name";
          type string;
        }
        leaf-list non-exist-map-list {
          description
            "condition route-map name";
          type string;
        }
        leaf exist-map {
          status obsolete;
          description
            "condition route-map name (OBSOLETE) - Please use exist-map-list
             instead";
          type string;
        }
        leaf non-exist-map {
          status obsolete;
          description
            "condition route-map name (OBSOLETE) - Please use non-exist-map
             instead";
          type string;
        }
        must 'exist-map-list or non-exist-map-list' {
          error-message "Either exist-map or non-exist-map must be configured";
        }
      }
    }
  }

  grouping neighbor-advertisement-interval-grouping {
    leaf advertisement-interval {
      description
        "Minimum interval between sending BGP routing updates";
      type uint16 {
        range "0..600";
      }
    }
  }

  grouping neighbor-advertisement-interval-ebgp-grouping {
    leaf advertisement-interval-ebgp {
      status deprecated;
      description
        "Minimum interval between sending BGP routing updates for eBGP peers(DEPRECATED)";
      type uint16 {
        range "0..600";
      }
    }
  }

  grouping neighbor-aigp-grouping {
    container aigp {
      description
        "Enable a AIGP on neighbor";
      presence "true";
      container send {
        description
          "Cost community or MED carrying AIGP VALUE";
        choice send-options {
          case cost-community {
            container cost-community {
              description
                "Cost extended community carrying AIGP Value";
              leaf community-id {
                description
                  "Community ID";
                type uint8 {
                  range "0..255";
                }
              }
              leaf poi-leaf {
                description
                  "Point of insertion";
                type enumeration {
                  enum igp-cost;
                  enum pre-bestpath;
                }
              }
              leaf transitive {
                description
                  "Cost community is transitive";
                when '../poi-leaf';
                type empty;
              }
              container poi {
                description
                  "Point of insertion (OBSOLETE)";
                status obsolete;
                choice poi-options {
                  status obsolete;
                  case igp-cost {
                    status obsolete;
                    container igp-cost {
                      description
                        "Point of insertion after IGP (OBSOLETE)";
                      status obsolete;
                      presence "true";
                      leaf transitive {
                        status obsolete;
                        description
                          "Cost community is transitive (OBSOLETE)";
                        type empty;
                      }
                    }
                  }
                  case pre-bestpath {
                    status obsolete;
                    container pre-bestpath {
                      description
                        "Point of insertion at beginning (OBSOLETE)";
                      status obsolete;
                      presence "true";
                      leaf transitive {
                        status obsolete;
                        description
                          "Cost community is transitive (OBSOLETE)";
                        type empty;
                      }
                    }
                  }
                }
              }
            }
          }
          case med {
            leaf med {
              description
                "Med carrying AIGP Value";
              type empty;
            }
          }
        }
      }
    }
  }

  grouping neighbor-allow-policy-grouping {
    leaf allow-policy {
      description
        "Enable the policy support for this IBGP Neighbor";
      type empty;
    }
  }

  grouping neighbor-allowas-in-grouping {
    container allowas-in {
      description
        "Accept as-path with my AS present in it";
      presence "accept as-paths";
      leaf as-number {
        type uint8 {
          range "1..10";
        }
      }
    }
  }

  grouping neighbor-announce-grouping {
    container announce {
      description
        "Announce RPKI state using an extended community";
      container rpki {
        description
          "Announce RPKI information using an extended community";
        leaf state {
          description
            "Announce RPKI state information using an extended community";
          type empty;
          must "((../../../ios-bgp:send-community/ios-bgp:send-community-where = 'extended') or (../../../ios-bgp:send-community/ios-bgp:send-community-where = 'both'))" {
            error-message "Configure neighbor send-community extended before rpki";
          }
        }
      }
    }
  }

  grouping neighbor-as-override-grouping {
    container as-override {
      description
        "Override matching AS-number while sending update";
      presence "true";
      leaf split-horizon {
        type empty;
      }
    }
  }

  grouping neighbor-capability-peer-group-grouping {
    leaf prefix-list-send {
      description
        "Advertise prefix list ORF capability to this neighbor";
      type enumeration {
        enum send;
      }
    }
  }

  grouping neighbor-capability-grouping {
    container capability {
      description
        "Advertise capability to the peer";
      container orf {
        description
          "Advertise ORF capability to the peer";
        leaf-list prefix-list {
          description
            "Advertise prefix list ORF capability to this neighbor";
          max-elements 1;
          type enumeration {
            enum both;
            enum receive;
            enum send;
          }
        }
      }
    }
  }

  grouping neighbor-default-originate-grouping {
    container default-originate {
      description
        "Originate default route to this neighbor";
      presence "enable originate default route to this neighbor";
      leaf route-map {
        description
          "Route-map to specify criteria to originate default";
        type string;
      }
    }
  }

  grouping rtfilter-neighbor-default-originate-grouping {
    leaf default-originate-rtfilter {
      description
        "Originate default route to this neighbor";
      type empty;
    }
  }

  grouping neighbor-distribute-list-grouping {
    list distribute-list {
      description
        "Filter updates to/from this neighbor";
      key "inout";
      leaf inout {
        type enumeration {
          enum in;
          enum out;
        }
      }
      leaf accesslist {
        type ios-types:bgp-distribute-list-type2;
        mandatory true;
      }
    }
  }

  grouping neighbor-dmzlink-bw-grouping {
    leaf dmzlink-bw {
      description
        "Propagate the DMZ link bandwidth";
      type empty;
    }
  }

  grouping neighbor-encap-grouping {
    container encap {
      description
        "Preferred encapsulation for neighbor";
      choice encap-choice {
        leaf mpls {
          description
            "Neighbor prefers MPLS";
          type empty;
        }
        leaf vxlan {
          description
            "Neighbor prefers VxLAN";
          type empty;
        }
      }
    }
  }

  grouping neighbor-filter-list-grouping {
    list filter-list {
      description
        "Establish BGP filters";
      key "inout";
      leaf inout {
        type enumeration {
          enum in;
          enum out;
        }
      }
      leaf as-path-list {
        type uint16 {
          range "1..500";
        }
        mandatory true;
      }
    }
  }

  grouping template-filter-list-grouping {
    list filter-list1 {
      description
        "Establish BGP filters";
      key "inout";
      leaf inout {
        type enumeration {
          enum in;
          enum out;
        }
      }
      leaf as-path-list {
        type uint16 {
          range "1..500";
        }
        mandatory true;
      }
    }
  }

  grouping neighbor-internal-vpn-client-grouping {
    leaf internal-vpn-client {
      description
        "Stack iBGP-CE Neighbor Path in ATTR SET for VPN update";
      type empty;
    }
  }

  grouping neighbor-maximum-prefix-grouping {
    container maximum-prefix {
      description
        "Maximum number of prefixes accepted from this peer";
      leaf max-prefix-no {
        description
          "maximum no. of prefix limit";
        type uint32 {
          range "1..2147483647";
        }
      }
      leaf threshold {
        when '(../max-prefix-no)';
        default "75";
        type uint8 {
          range "1..100";
        }
      }
      leaf restart {
        description
          "Restart bgp connection after limit is exceeded";
        type uint16 {
          range "1..65535";
        }
        must 'not(../warning-only)' {
          error-message
            "restart and warning-only cannot be configured at the
             same time";
        }
      }
      leaf warning-only {
        description
          "Only give warning message when limit is exceeded";
        type empty;
      }
      must '(max-prefix-no) or (not(max-prefix-no) and not(threshold) and not(restart) and not(warning-only))' {
        error-message "max-prefix-no must be configured";
      }
    }
  }

  grouping address-family-mvpn-select-grouping {
    container mvpn {
      description
        "Configure mvpn";
      container single-forwarder-selection {
        description
          "Configure mvpn single-forwarder-selection";
        leaf highest-ip-address {
          description
            "Select highest ip address";
          type empty;
        }
      }
    }
  }

  grouping neighbor-next-hop-self-grouping {
    container next-hop-self {
      description
        "Disable the next hop calculation for this neighbor";
      presence "true";
      leaf all {
        description
          "Enable next-hop-self for both eBGP and iBGP received paths";
        type empty;
      }
    }
  }

  grouping neighbor-next-hop-unchanged-grouping {
    leaf next-hop-unchanged {
      status obsolete;
      description
        "Propagate the iBGP paths' next hop unchanged for this neighbor
         (OBSOLETE) - Please us nexthop-unchanged/next-hop-unchanged instead.";
      type empty;
    }
  }

  grouping neighbor-next-hop-unchanged-v2-grouping {
    container nexthop-unchanged {
      description
        "Propagate the iBGP paths' next hop unchanged for this neighbor";
      leaf next-hop-unchanged {
        description
          "Propagate the iBGP paths' next hop unchanged for this neighbor";
        type empty;
      }
      leaf allpaths {
        when '../next-hop-unchanged';
        description
          "Propagate next hop unchanged for all iBGP paths to this neighbor";
        type empty;
      }
    }
  }

  grouping vrf-neighbor-next-hop-unchanged-grouping {
    leaf next-hop-unchanged {
      status obsolete;
      description
        "Propagate the iBGP paths' next hop unchanged for this neighbor (OBSOLETE)";
      type empty;
      must '(../ios-bgp:ebgp-multihop or /ios:native/ios:router/ios-bgp:bgp/ios-bgp:id = ../remote-as)' {
        error-message
          "Can propagate the nexthop only to multi-hop EBGP neighbor
           or iBGP VRF CE lite";
      }
    }
  }

  grouping vrf-neighbor-next-hop-unchanged-v2-grouping {
    container nexthop-unchanged {
      description
        "Propagate the iBGP paths' next hop unchanged for this neighbor";
      leaf next-hop-unchanged {
        description
          "Propagate the iBGP paths' next hop unchanged for this neighbor";
        type empty;
        must '(../../ios-bgp:ebgp-multihop or /ios:native/ios:router/ios-bgp:bgp/ios-bgp:id = ../../remote-as)' {
          error-message
            "Can propagate the nexthop only to multi-hop EBGP neighbor
             or iBGP VRF CE lite";
        }
      }
      leaf allpaths {
        when '../next-hop-unchanged';
        description
          "Propagate next hop unchanged for all iBGP paths to this neighbor";
        type empty;
      }
    }
  }

  grouping neighbor-peer-group-grouping {
    container peer-group {
      description
        "Member of the peer-group";
      leaf peer-group-name {
        description
          "peer-group name";
        type string;
      }
    }
  }

  grouping neighbor-peer-group-obsolete-grouping {
    container peer-group {
      status obsolete;
      description
        "Member of the peer-group (OBSOLETE)";
      leaf peer-group-name {
        status obsolete;
        description
          "peer-group name (OBSOLETE)";
        type string;
      }
    }
  }

  grouping peer-group-peer-group-grouping {
    leaf peer-group {
      description
        "Member of the peer-group";
      type empty;
      mandatory true;
    }
  }

  grouping neighbor-prefix-length-size-grouping {
    leaf prefix-length-size {
      description
        "Storage size in bytes";
      type uint16 {
        range "1..2";
      }
    }
  }

  grouping neighbor-prefix-list-grouping {
    list prefix-list {
      description
        "Filter updates to/from this neighbor";
      key "inout";
      leaf inout {
        type enumeration {
          enum in;
          enum out;
        }
      }
      leaf prefix-list-name {
        type string;
        mandatory true;
      }
    }
  }

  grouping neighbor-remove-private-as-grouping {
    container remove-private-as {
      description
        "Remove private AS number from outbound updates";
      presence "true";
      container all {
        description
          "Remove all private AS numbers";
        presence "true";
        leaf replace-as {
          description
            "Replace all private AS numbers with local AS";
          type empty;
        }
      }
    }
  }

  grouping neighbor-route-map-grouping {
    list route-map {
      description
        "Apply route map to neighbor";
      key "inout";
      leaf inout {
        type enumeration {
          enum in;
          enum out;
        }
      }
      leaf route-map-name {
        type string;
        mandatory true;
      }
    }
  }

  grouping template-route-map-grouping {
    list route-map1 {
      description
        "Apply route map to neighbor";
      key "inout";
      leaf inout {
        type enumeration {
          enum in;
          enum out;
        }
      }
      leaf route-map-name {
        type string;
        mandatory true;
      }
    }
  }

  grouping neighbor-route-reflector-client-grouping {
    leaf route-reflector-client {
      description
        "Configure a neighbor as Route Reflector client";
      type empty;
    }
  }

  grouping neighbor-send-community-grouping {
    container send-community {
      description
        "Send Community attribute to this neighbor";
      presence "true";
      leaf send-community-where {
        default "standard";
        type enumeration {
          enum both;
          enum extended;
          enum standard;
        }
      }
    }
  }

  grouping vrf-neighbor-send-label-grouping {
    leaf send-label-vrf {
      description
        "Send NLRI + MPLS Label to this peer";
      type empty;
    }
  }

  grouping neighbor-send-label-grouping {
    container send-label {
      description
        "Send NLRI + MPLS Label to this peer";
      presence "true";
      leaf send-label-explicit {
        type enumeration {
          enum explicit-null;
        }
      }
    }
  }

  grouping neighbor-slow-peer-grouping {
    container slow-peer {
      description
        "Configure slow-peer";
      container detection {
        description
          "Slow-peer detection";
        presence "true";
        leaf threshold {
          description
            "Threshold value (seconds)";
          type uint16 {
            range "120..3600";
          }
        }
        leaf disable {
          description
            "Disable slow-peer detection";
          type empty;
        }
        must "(not(threshold) and disable) or (threshold and not(disable)) or
              (not(threshold) and not(disable))" {
          error-message "threshold and disable can't be configured at the same time";
        }
      }
      container split-update-group {
        description
          "Configure slow-peer split-update-group";
        container dynamic {
          description
            "Dynamically split the slow peer to slow-update group";
          presence "true";
          leaf permanent {
            description
              "Keep the slow-peer permanently in slow-update group";
            type empty;
          }
          leaf disable {
            description
              "Disable slow-peer detection";
            type empty;
          }
          must "(not(permanent) and disable) or (permanent and not(disable)) or
                (not(permanent) and not(disable))" {
            error-message "threshold and disable can't be configured at the same time";
          }
        }
        leaf static {
          description
            "Static slow-peer";
          type empty;
        }
      }
    }
  }

  grouping neighbor-soft-reconfiguration-grouping {
    leaf soft-reconfiguration {
      description
        "Per neighbor soft reconfiguration";
      type enumeration {
        enum inbound;
      }
    }
  }

  grouping neighbor-soo-grouping {
    leaf soo {
      description
        "ASN:nn or IP-address:nn VPN extended community";
      type string {
        pattern '[0-9]*:[0-9]*|[0-9.]*:[0-9]*';
      }
    }
  }

  grouping neighbor-suppress-signaling-protocol-grouping {
    container suppress-signaling-protocol {
      description
        "suppress VPLS signaling protocol";
      leaf ldp {
        description
          "suppress ldp signaling, enable bgp signaling";
        type empty;
      }
    }
  }

  grouping neighbor-translate-update-grouping {
    container translate-update {
      description
        "Translate update to MBGP format";
      container multicast {
        description
          "Address Family modifier";
        presence "Address Family modifier";
        leaf unicast {
          description
            "Address Family modifier";
          type empty;
        }
      }
      container ipv4 {
        status obsolete;
        description
          "Address Family (OBSOLETE)";
        container multicast {
          status obsolete;
          description
            "Address Family modifier (OBSOLETE)";
          presence "Address Family modifier";
          leaf unicast {
            status obsolete;
            description
              "Address Family modifier (OBSOLETE)";
            type empty;
          }
        }
      }
    }
  }

  grouping neighbor-unsuppress-map-grouping {
    leaf unsuppress-map {
      description
        "Route-map to selectively unsuppress suppressed routes";
      type string;
    }
  }

  grouping neighbor-validation-grouping {
    container validation {
      description
        "Validation of flowspec paths";
      leaf off {
        description
          "Disable all validations except on Redirect-IP ext comm";
        type empty;
      }
      leaf redirect-off {
        description
          "Disable validations on Redirect-IP ext comm";
        type empty;
      }
    }
  }

  grouping neighbor-weight-grouping {
    leaf weight {
      description
        "Set default weight for routes from this neighbor";
      type uint16 {
        range "0..65535";
      }
    }
  }

  grouping neighbor-bmp-activate-grouping {
    container bmp-activate {
      description
        "Activate the BMP monitoring for a BGP peer";
      choice bmp-activate-choice {
        leaf all {
          description
            "Activate BMP monitoring for all servers";
          type empty;
        }
        container server-list {
          description
            "Activate BMP for server";
          leaf server-1 {
            description
              "Activate BMP for server-1";
            type enumeration {
              enum 1;
            }
          }
          leaf server-2 {
            description
              "Activate BMP for server-2";
            type enumeration {
              enum 2;
            }
          }
          leaf server-3 {
            description
              "Activate BMP for server-3";
            type enumeration {
              enum 3;
            }
          }
          leaf server-4 {
            description
              "Activate BMP for server-4";
            type enumeration {
              enum 4;
            }
          }
        }
      }
    }
  }

  grouping neighbor-cluster-id-grouping {
    leaf cluster-id {
      type union {
        type uint32 {
          range "1..4294967294";
        }
        type inet:ipv4-address;
      }
      must '/ios:native/ios:router/ios-bgp:bgp/ios-bgp:id = ../remote-as' {
        error-message "cluster-id only allowed for IBGP peers";
      }
    }
  }

  grouping neighbor-description-grouping {
    leaf description {
      description
        "Neighbor specific description";
      type string;
    }
  }

  grouping neighbor-disable-connected-check-grouping {
    leaf disable-connected-check {
      description
        "one-hop away EBGP peer using loopback address";
      type empty;
      must '(../remote-as != /ios:native/ios:router/ios-bgp:bgp/ios-bgp:id)' {
        error-message "allowed only for eBGP peers";
      }
    }
  }

  grouping neighbor-dont-capability-negotiate-grouping {
    container dont-capability-negotiate {
      description
        "Send Capability parameters in Open";
      presence "true";
      leaf enhanced-refresh {
        description
          "Suppress Enhanced Refresh capability in Open";
        type empty;
      }
      leaf four-octets-as {
        description
          "Suppress Four-octet ASN capability in Open";
        type empty;
      }
    }
  }

  grouping neighbor-ebgp-multihop-grouping {
    container ebgp-multihop {
      description
        "Allow EBGP neighbors not on directly connected networks. For
         single-hop ebgp peers, delete ebgp-multihop directly.";
      presence "ebgp-multihop parameters";
      leaf max-hop {
        type uint8 {
          range "2..255";
        }
        default "255";
      }
    }
  }

  grouping neighbor-fall-over-grouping {
    container fall-over {
      description
        "session fall on peer route lost";
      container default {
        leaf enable {
          type empty;
        }
        leaf route-map {
          type string;
        }
      }
      container bfd {
        description
          "Use BFD to detect failure";
        presence "true";
        choice hop-choice {
          leaf multi-hop {
            description
              "Force BFD multi-hop to detect failure";
            type empty;
          }
          leaf single-hop {
            description
              "Force BFD single-hop to detect failure";
            type empty;
          }
        }
        leaf check-control-plane-failure {
          description
            "Retrieve control plane dependent failure info from BFD for BGP
             GR/NSR operation";
          type empty;
        }
        leaf strict-mode {
          description
            "Enable BFD strict-mode";
          type empty;
        }
      }
      container maximum-metric {
        presence "true";
        leaf route-map {
          type string;
        }
      }
    }
  }

  grouping neighbor-ha-mode-grouping {
    container ha-mode {
      description
        "high availability mode";
      container graceful-restart {
        description
          "graceful-restart for this peer";
        presence "true";
        leaf disable {
          description
            "disable graceful-restart";
          type empty;
        }
      }
      container sso {
        description
          "stateful-switchover support for this peer";
        presence "true";
        leaf disable {
          description
            "disable stateful-switchover";
          type empty;
        }
      }
    }
  }

  grouping neighbor-inherit-grouping {
    container inherit {
      description
        "Inherit a template";
      leaf peer-policy {
        description
          "Inherit a peer-policy template";
        type string;
      }
      leaf peer-session {
        description
          "Inherit a peer-session template";
        type string;
      }
    }
  }

  grouping template-peer-session-inherit-grouping {
    container inherit {
      description
        "Inherit a template";
      leaf peer-policy {
        status obsolete;
        description
          "Inherit a peer-policy template (OBSOLETE)";
        type string;
      }
      leaf peer-session {
        description
          "Inherit a peer-session template";
        type string;
      }
    }
  }

  grouping neighbor-af-inherit-grouping {
    container inherit {
      description
        "Inherit a template";
      leaf peer-policy {
        description
          "Inherit a peer-policy template";
        type leafref {
          path "/ios:native/ios:router/ios-bgp:bgp/ios-bgp:template/ios-bgp:peer-policy/ios-bgp:name";
        }
      }
      leaf peer-session {
        status obsolete;
        description
          "Inherit a peer-session template (OBSOLETE)";
        type string;
      }
    }
  }

  grouping global-neighbor-inherit-grouping {
    container inherit {
      description
        "Inherit a template";
      leaf peer-session {
        description
          "Inherit a peer-session template";
        type leafref {
          path "/ios:native/ios:router/ios-bgp:bgp/ios-bgp:template/ios-bgp:peer-session/ios-bgp:name";
        }
      }
      leaf peer-policy {
        status obsolete;
        description
          "Inherit a peer-policy template (OBSOLETE)";
        type string;
      }
    }
  }

  grouping peer-group-inherit-grouping {
    container inherit {
      status obsolete;
      description
        "Inherit a template";
      leaf peer-policy {
        status obsolete;
        description
          "Inherit a peer-policy template (OBSOLETE)";
        type string;
      }
      leaf peer-session {
        status obsolete;
        description
          "Inherit a peer-session template (OBSOLETE)";
        type string;
      }
    }
  }

  grouping neighbor-inter-as-hybrid-grouping {
    leaf inter-as-hybrid {
      description
        "Inter AS Hybrid mode";
      type empty;
    }
  }

  grouping neighbor-long-lived-grouping {
    container long-lived-graceful-restart {
      description
        "Enable long-lived-graceful-restart";
      container stale-time-choice {
        description
          "Maximum time to wait before purging long-lived stale routes";
        choice stale-time-choice {
          container with-send-option {
            presence "true";
            leaf send {
              description
                "Stale-time sent in capability";
              mandatory true;
              type uint32 {
                range "0..4294967";
              }
            }
            leaf accept {
              description
                "Maximum stale-time acceptable from neighbor";
              mandatory true;
              type uint32 {
                range "0..4294967";
              }
            }
          }
          container without-send-option {
            leaf accept {
              description
                "Maximum stale-time acceptable from neighbor";
              type uint32 {
                range "0..4294967";
              }
            }
          }
        }
      }
      container stale-time {
        description
          "Maximum time to wait before purging long-lived stale routes";
        status deprecated;
        leaf send {
          status deprecated;
          description
            "Stale-time sent in capability";
          when '../accept';
          type uint32 {
            range "0..4294967";
          }
        }
        leaf accept {
          status deprecated;
          description
            "Maximum stale-time acceptable from neighbor";
          type uint32 {
            range "0..4294967";
          }
        }
      }
    }
  }

  grouping neighbor-local-as-grouping {
    container local-as {
      description
        "Specify a local-as number";
      presence "Specify a local-as number";
      leaf as-no {
        type ios-types:bgp-as-number-type;
      }
      leaf no-prepend {
        when '../as-no';
        description
          "Do not prepend local-as to updates from ebgp peers";
        type empty;
        must '(../../remote-as != ../as-no)' {
          error-message "iBGP local-as dual-as cannot have configured no-prepend/replace-as";
        }
      }
      leaf replace-as {
        when '../no-prepend';
        description
          "Replace real AS with local AS in the EBGP updates";
        type empty;
      }
      leaf dual-as {
        description
          "Accept either real AS or local AS from the ebgp peer";
        type empty;
        must '(../../remote-as = ../as-no) or (../no-prepend or ../replace-as)' {
          error-message "dual-as not allowed without no-prepend/replace-as for eBGP local-as";
        }
      }
      must '(../remote-as != /ios:native/ios:router/ios-bgp:bgp/ios-bgp:id) and (as-no != /ios:native/ios:router/ios-bgp:bgp/ios-bgp:id)' {
        error-message "local-as not allowed for true (non-local-as) iBGP peers and local-as should not be same as global-as number";
      }
    }
  }

  grouping neighbor-peer-group-local-as-grouping {
    container local-as {
      description
        "Specify a local-as number";
      presence "Specify a local-as number";
      leaf as-no {
        type ios-types:bgp-as-number-type;
      }
      leaf no-prepend {
        when '../as-no';
        description
          "Do not prepend local-as to updates from ebgp peers";
        type empty;
        must '(../../remote-as != ../as-no)' {
          error-message "iBGP local-as dual-as cannot have configured no-prepend/replace-as";
        }
      }
      leaf replace-as {
        when '../no-prepend';
        description
          "Replace real AS with local AS in the EBGP updates";
        type empty;
      }
      leaf dual-as {
        description
          "Accept either real AS or local AS from the ebgp peer";
        type empty;
        must '(../../remote-as = ../as-no) or (../no-prepend or ../replace-as)' {
          error-message "dual-as not allowed without no-prepend/replace-as for eBGP local-as";
        }
      }
    }
  }

  grouping neighbor-log-neighbor-changes-grouping {
    container log-neighbor-changes {
      description
        "Log neighbor up/down and reset reason";
      presence "true";
      leaf disable {
        description
          "disable";
        type empty;
      }
    }
  }

  grouping template-local-as-grouping {
    container local-as {
      description
        "Specify a local-as number";
      presence "Specify a local-as number";
      leaf as-no {
        type ios-types:bgp-as-number-type;
      }
      choice local-as-choice {
        case as-options {
          leaf no-prepend {
            when '../as-no';
            description
              "Do not prepend local-as to updates from ebgp peers";
            type empty;
          }
          leaf replace-as {
            when '../no-prepend';
            description
              "Replace real AS with local AS in the EBGP updates";
            type empty;
          }
          leaf dual-as {
            when '../replace-as';
            description
              "Accept either real AS or local AS from the ebgp peer";
            type empty;
          }
        }
        case dual-as-option {
          leaf dual-as-no {
            description
              "Accept either real AS or local AS from the ebgp peer";
            type empty;
          }
        }
      }
    }
  }

  grouping neighbor-password-grouping {
    container password {
      description
        "Set a password";
      leaf enctype {
        description
          "Encryption type (0 to disable encryption, 7 for proprietary)";
        type uint8 {
          range "0..7";
        }
      }
      leaf text {
        type string {
          pattern '.*';
          length "1..52";
        }
      }
      must '(not(text) and not(enctype)) or text' {
        error-message "password text must be configured";
      }
    }
  }

  grouping neighbor-ao-grouping {
    container ao {
      description
        "BGP AO security";
      leaf keychain-name {
        description
          "Key Chain Name";
        type string;
        must 'not(. and ../../password/text)' {
          error-message "Neighbor cannot have both password and ao keychain-name";
        }
      }
      leaf include-tcp-options {
        when '../keychain-name';
        description
          "Include TCP options";
        type empty;
      }
      leaf accept-ao-mismatch-connections {
        when '../keychain-name';
        description
          "accept ao mismatch connections";
        type empty;
      }
    }
  }

  grouping neighbor-path-attribute-grouping {
    container path-attribute {
      description
        "BGP optional attribute filtering";
      container discard {
        description
          "Discard matching path-attribute for this neighbor";
        uses bgp-path-range-grouping;
      }
      container treat-as-withdraw {
        description
          "Treat-as-withdraw matching path-attribute for this neighbor";
        uses bgp-path-range-grouping;
      }
    }
  }

  grouping bgp-path-range-grouping {
    list attribute-type {
      key "type";
      leaf type {
        description
          "path attribute type";
        type uint8 {
          range "1..255";
        }
      }
      leaf in {
        description
          "Perform inbound path-attribute filtering";
        mandatory true;
        type empty;
      }
    }
    container attibute_type {
      status obsolete;
      description
        "This node is obsolete and replaced by list attribute-type (OBSOLETE)";
      leaf type {
        status obsolete;
        description
          "path attribute type (OBSOLETE)";
        type uint8 {
          range "1..255";
        }
      }
      leaf in {
        status obsolete;
        description
          "Perform inbound path-attribute filtering (OBSOLETE)";
        type empty;
      }
    }
    container range {
      description
        "This node is deprecated and replaced by list range1";
      leaf start_value {
        description
          "path attribute range start value";
        type uint8 {
          range "1..255";
        }
      }
      leaf end_value {
        when '../start_value';
        description
          "path attribute range end value";
        type uint8 {
          range "1..255";
        }
      }
      leaf in {
        when '../end_value';
        description
          "Perform inbound path-attribute filtering";
        type empty;
      }
      must "(start_value and end_value and in) or (not(start_value) and
            not(end_value) and not(in))" {
        error-message
          "Start-value, end-value, and in must all be configured in
           the range.";
      }
    }
  }

  grouping neighbor-remote-as-grouping {
    leaf remote-as {
      description
        "Specify a BGP peer-group remote-as";
      type ios-types:bgp-as-number-type;
    }
  }

  grouping neighbor-shutdown-grouping {
    leaf shutdown {
      description
        "Administratively shut down this neighbor";
      type empty;
    }
  }

  grouping neighbor-timers-grouping {
    container timers {
      description
        "BGP per neighbor timers";
      leaf keepalive-interval {
        default "60";
        type uint16 {
          range "0..65535";
        }
      }
      leaf holdtime {
        default "180";
        type uint16 {
          range "0..65535";
        }
      }
      leaf minimum-neighbor-hold {
        default "0";
        type uint16 {
          range "0..65535";
        }
      }
      must '((keepalive-interval and holdtime) or ( not(keepalive-interval) and not(holdtime) and not(minimum-neighbor-hold))) and (((keepalive-interval < holdtime) and holdtime != 0) or ((keepalive-interval = 0) and (holdtime = 0)))' {
        error-message
          "Keepalive-interval and holdtime must be configured.
           Holdtime should be greater than the keepalive time.
           If holdtime is 0, keepalive time should also be 0";
      }
    }
  }

  grouping neighbor-transport-grouping {
    container transport {
      description
        "Transport options";
      leaf connection-mode {
        description
          "Specify passive or active connection";
        type enumeration {
          enum active;
          enum passive;
        }
      }
      leaf multi-session {
        description
          "Use multi-session for transport";
        type empty;
      }
      container path-mtu-discovery {
        description
          "Use transport path MTU discovery";
        presence "true";
        leaf disable {
          description
            "disable";
          type empty;
        }
      }
    }
  }

  grouping neighbor-ttl-security-grouping {
    container ttl-security {
      description
        "BGP ttl security check";
      leaf hops {
        description
          "IP hops";
        type uint8 {
          range "1..254";
        }
        must 'not(../../ios-bgp:ebgp-multihop)' {
          error-message "Remove ebgp-multihop before configuring ttl-security";
        }
      }
    }
  }

  grouping neighbor-update-grouping {
    container update {
      description
        "Modify update processing";
      container in {
        description
          "Modify inbound update processing";
        container labeled-unicast {
          description
            "Modify update processing for labeled-unicast SAFI";
          leaf unique {
            description
              "SAFI 1 and SAFI 4 processed independently";
            type empty;
          }
        }
      }
      container out {
        description
          "Modify outbound update processing";
        container labeled-unicast {
          description
            "Modify update processing for labeled-unicast SAFI";
          leaf unique {
            description
              "SAFI 1 and SAFI 4 processed independently";
            type empty;
          }
        }
      }
    }
  }

  grouping neighbor-update-source-grouping {
    container update-source {
      description
        "Source of routing updates";
      container interface {
        uses ios:interface-with-dependency-grouping;
      }
      uses ios-ifc:interface-deprecated-grouping;
    }
  }

  grouping neighbor-version-grouping {
    leaf version {
      description
        "Set the BGP version to match a neighbor";
      type uint16 {
        range "4";
      }
    }
  }

  grouping address-family-advertise-grouping {
    container advertise {
      description
        "Configure path advertise/export to other address-family";
      container l2vpn {
        description
          "Address family for VRF advertise/export";
        leaf evpn {
          description
            "Advertise/export prefixes to l2vpn evpn table";
          type empty;
        }
        leaf allow-suppressed {
          description
            "also advertise suppressed routes";
          type empty;
          when '../evpn';
        }
        leaf evpn-prefix-limit {
          description
            "Upper limit on advertise/export prefixes without
             hogging memory";
          when '../evpn';
          type uint32 {
            range "1..2147483647";
          }
        }
      }
    }
  }

  grouping address-family-ipv4-aggregate-address-grouping {
    list aggregate-address {
      description
        "Configure BGP aggregate entries";
      key "ipv4-address ipv4-mask";
      leaf ipv4-address {
        type inet:ipv4-address;
      }
      leaf ipv4-mask {
        type inet:ipv4-address;
      }
      leaf as-confed-set {
        description
          "Generate AS confed set path information";
        type empty;
        must 'not(../as-set)' {
          error-message
            "as-confed-set and as-set cannot be configured at the
             same time";
        }
      }
      leaf as-set {
        description
          "Generate AS set path information";
        type empty;
      }
      leaf summary-only {
        description
          "Filter more specific routes from updates";
        type empty;
      }
      leaf attribute-map {
        description
          "Route map for parameter control";
        type string;
      }
      leaf as-override {
        status obsolete;
        description
          "Override matching AS-number while sending update (OBSOLETE)";
        type empty;
      }
      leaf route-map {
        status obsolete;
        description
          "OBSOLETE";
        type string;
      }
      leaf advertise-map {
        description
          "Set condition to advertise attribute";
        type string;
      }
      leaf suppress-map {
        description
          "Conditionally filter more specific routes from updates";
        type string;
      }
    }
  }

  grouping address-family-ipv6-aggregate-address-grouping {
    list aggregate-address {
      description
        "Configure BGP aggregate entries";
      key "ipv6-address";
      leaf ipv6-address {
        type ios-types:ipv6-prefix;
      }
      leaf advertise-map {
        description
          "Set condition to advertise attribute";
        type string;
      }
      leaf as-confed-set {
        description
          "Generate AS confed set path information";
        type empty;
        must 'not(../as-set)' {
          error-message
            "as-confed-set and as-set cannot be configured at the
             same time";
        }
      }
      leaf as-set {
        description
          "Generate AS set path information";
        type empty;
      }
      leaf attribute-map {
        type string;
      }
      leaf as-override {
        status obsolete;
        description
          "Override matching AS-number while sending update (OBSOLETE)";
        type empty;
      }
      leaf route-map {
        status obsolete;
        description
          "OBSOLETE - Please use attribute-map";
        type string;
      }
      leaf summary-only {
        description
          "Filter more specific routes from updates";
        type empty;
      }
      leaf suppress-map {
        description
          "Conditionally filter more specific routes from updates";
        type string;
      }
    }
  }

  grouping address-family-auto-summary-grouping {
    leaf auto-summary {
      description
        "Enable automatic network number summarization";
      type empty;
    }
  }

  grouping address-family-default-information-grouping {
    container default-information {
      description
        "Control distribution of default information";
      leaf originate {
        description
          "Distribute a default route";
        type empty;
      }
    }
  }

  grouping address-family-default-metric-grouping {
    leaf default-metric {
      description
        "Set metric of redistributed routes";
      type uint32 {
        range "1..4294967295";
      }
    }
  }

  grouping address-family-distance-grouping {
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
        must '(extern-as and internal-as and local) or (not(extern-as) and not(internal-as) and not(local))' {
          error-message "external-as, internal-as, and local  must be configured";
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern '[a-zA-Z].*';
            }
          }
        }
      }
    }
  }

  grouping address-family-ipv6-distance-grouping {
    container distance {
      description
        "Define an administrative distance";
      container bgp {
        description
          "BGP distance";
        leaf extern-as {
          description
            "Distance for routes external to the AS";
          type uint16 {
            range "1..255";
          }
        }
        leaf internal-as {
          description
            "Distance for routes internal to the AS";
          type uint16 {
            range "1..255";
          }
        }
        leaf local {
          description
            "Distance for local routes";
          type uint16 {
            range "1..255";
          }
        }
        must '(extern-as and internal-as and local) or (not(extern-as) and not(internal-as) and not(local))' {
          error-message "external-as, internal-as, and local  must be configured";
        }
      }
      list adm-distance {
        key "distance src-ipv6-address";
        leaf distance {
          description
            "Administrative distance";
          type uint16 {
            range "1..255";
          }
        }
        leaf src-ipv6-address {
          description
            "Prefix to match source address";
          type ios-types:ipv6-prefix;
        }
        leaf prefix-list-name {
          description
            "IPv6 prefix list name to match routes from the source";
          type string;
        }
      }
    }
  }

  grouping address-family-ipv6-distance-grouping-2 {
    list adm-distance-v6 {
      key "distance src-ipv6-address";
      leaf distance {
        description
          "Administrative distance";
        type uint16 {
          range "1..255";
        }
      }
      leaf src-ipv6-address {
        description
          "Prefix to match source address";
        type ios-types:ipv6-prefix;
      }
      leaf prefix-list-name {
        description
          "IPv6 prefix list name to match routes from the source";
        type string;
      }
    }
  }

  grouping address-family-distribute-list-grouping {
    container distribute-list {
      description
        "Filter networks in routing updates";
      uses address-family-distribute-list-with-interface-grouping;
      list accesslist {
        key "acl in-out";
        leaf acl {
          description
            "Access-list number or name";
          type union {
            type uint16 {
              range "1..199";
            }
            type uint16 {
              range "1300..1999";
            }
            type string {
              pattern '[a-zA-Z].*';
            }
          }
        }
        leaf in-out {
          description
            "Filter incoming or out-going update";
          mandatory true;
          type ios-types:access-list-in-out-type;
        }
        container interface {
          status obsolete;
          description
            "Interface name (Interface container is obsolete).";
          choice interface-choice {
            status obsolete;
            leaf AppNav-Compress {
              status obsolete;
              description
                "Service-Context Virtual Interface Compress";
              type uint16;
            }
            leaf AppNav-UnCompress {
              status obsolete;
              description
                "Service-Context Virtual Interface UnCompress";
              type uint16;
            }
            leaf ATM {
              status obsolete;
              description
                "ATM interface";
              type string;
            }
            container ATM-subinterface {
              status obsolete;
              leaf ATM {
                status obsolete;
                type string;
              }
            }
            leaf ATM-ACR {
              status obsolete;
              description
                "ATM-ACR interface";
              type string {
                pattern '[0-9]';
              }
            }
            container ATM-ACRsubinterface {
              status obsolete;
              leaf ATM-ACR {
                status obsolete;
                type string {
                  pattern '[0-9]\.([0-9]/){3}[0-9]';
                }
              }
            }
            leaf BDI {
              status obsolete;
              description
                "Bridge-Domain interface";
              type string;
            }
            leaf CEM {
              status obsolete;
              description
                "CEM interface";
              type string {
                pattern '([0-9]/){2}[0-9]';
              }
            }
            leaf CEM-ACR {
              status obsolete;
              description
                "CEM-ACR interface";
              type uint8 {
                range "0..255";
              }
            }
            leaf Embedded-Service-Engine {
              status obsolete;
              description
                "cisco embedded service engine module";
              type string;
            }
            leaf Ethernet {
              status obsolete;
              description
                "IEEE 802.3";
              type string;
            }
            leaf FastEthernet {
              status obsolete;
              description
                "FastEthernet IEEE 802.3";
              type string;
            }
            leaf GigabitEthernet {
              status obsolete;
              description
                "GigabitEthernet IEEE 802.3z";
              type string;
            }
            leaf FiveGigabitEthernet {
              status obsolete;
              description
                "Five GigabitEthernet ";
              type string;
            }
            leaf AppGigabitEthernet {
              status obsolete;
              description
                "App-hosting Gigabit Ethernet IEEE 802.3z";
              type string;
            }
            leaf TwentyFiveGigE {
              status obsolete;
              description
                "Twenty Five GigabitEthernet ";
              type string;
            }
            leaf TwoGigabitEthernet {
              status obsolete;
              description
                "Two GigabitEthernet ";
              type string;
            }
            leaf FortyGigabitEthernet {
              status obsolete;
              description
                "Forty GigabitEthernet ";
              type string;
            }
            leaf HundredGigE {
              status obsolete;
              description
                "Hundred GigabitEthernet";
              type string;
            }
            leaf LISP {
              status obsolete;
              description
                "Locator/ID Separation Protocol Virtual Interface";
              type string;
            }
            container LISP-subinterface {
              status obsolete;
              description
                "Locator/ID Separation Protocol Virtual Interface";
              leaf LISP {
                status obsolete;
                type string {
                  pattern '[0-9]*(. ?[1-9][0-9]*)*';
                }
              }
            }
            leaf Loopback {
              status obsolete;
              description
                "Loopback interface";
              type uint32;
            }
            leaf Multilink {
              status obsolete;
              description
                "Multilink-group interface";
              type uint16;
            }
            leaf nve {
              status obsolete;
              description
                "Network virtualization endpoint interface";
              type uint16;
            }
            leaf overlay {
              status obsolete;
              description
                "Overlay interface";
              type uint16;
            }
            leaf Port-channel {
              status obsolete;
              description
                "Ethernet Channel of interfaces";
              type uint32;
            }
            container Port-channel-subinterface {
              status obsolete;
              leaf Port-channel {
                status obsolete;
                type string;
              }
            }
            leaf pseudowire {
              status obsolete;
              description
                "Pseudowire Interface";
              type uint32;
            }
            leaf SM {
              status obsolete;
              description
                "SM Interface";
              type string;
            }
            leaf Cellular {
              status obsolete;
              description
                "Cellular Interface";
              type string;
            }
            leaf Dialer {
              status obsolete;
              description
                "Dialer Interface";
              type string;
            }
            leaf Serial {
              status obsolete;
              description
                "Serial interface";
              type string;
            }
            leaf TenGigabitEthernet {
              status obsolete;
              description
                "Ten Gigabit Ethernet";
              type string;
            }
            leaf Tunnel {
              status obsolete;
              description
                "Tunnel interface";
              type uint32;
            }
            leaf Virtual-Template {
              status obsolete;
              description
                "Virtual Template interface";
              type uint16;
            }
            leaf Vlan {
              status obsolete;
              description
                "Iosxr Vlans";
              type uint16;
            }
            leaf VirtualPortGroup {
              status obsolete;
              description
                "Virtual Port Group";
              type uint16;
            }
            leaf vasileft {
              status obsolete;
              description
                "vasileft";
              type uint16;
            }
            leaf vasiright {
              status obsolete;
              description
                "vasiright";
              type uint16;
            }
            leaf BD-VIF {
              status obsolete;
              description
                "Bridge-Domain Virtual IP interface";
              type string;
            }
          }
        }
      }
      list prefix-gateway-name {
        key "prefix-gateway name in-out";
        leaf prefix-gateway {
          type enumeration {
            enum prefix;
            enum gateway;
          }
        }
        leaf name {
          description
            "Prefix-list name";
          type string;
        }
        leaf in-out {
          description
            "Filter incoming or out-going update";
          type ios-types:access-list-in-out-type;
        }
        container interface {
          status obsolete;
          description
            "Interface name (Interface container is obsolete).";
          choice interface-choice {
            status obsolete;
            leaf AppNav-Compress {
              status obsolete;
              description
                "Service-Context Virtual Interface Compress";
              type uint16;
            }
            leaf AppNav-UnCompress {
              status obsolete;
              description
                "Service-Context Virtual Interface UnCompress";
              type uint16;
            }
            leaf ATM {
              status obsolete;
              description
                "ATM interface";
              type string;
            }
            container ATM-subinterface {
              status obsolete;
              leaf ATM {
                status obsolete;
                type string;
              }
            }
            leaf ATM-ACR {
              status obsolete;
              description
                "ATM-ACR interface";
              type string {
                pattern '[0-9]';
              }
            }
            container ATM-ACRsubinterface {
              status obsolete;
              leaf ATM-ACR {
                status obsolete;
                type string {
                  pattern '[0-9]\.([0-9]/){3}[0-9]';
                }
              }
            }
            leaf BDI {
              status obsolete;
              description
                "Bridge-Domain interface";
              type string;
            }
            leaf CEM {
              status obsolete;
              description
                "CEM interface";
              type string {
                pattern '([0-9]/){2}[0-9]';
              }
            }
            leaf CEM-ACR {
              status obsolete;
              description
                "CEM-ACR interface";
              type uint8 {
                range "0..255";
              }
            }
            leaf Embedded-Service-Engine {
              status obsolete;
              description
                "cisco embedded service engine module";
              type string;
            }
            leaf Ethernet {
              status obsolete;
              description
                "IEEE 802.3";
              type string;
            }
            leaf FastEthernet {
              status obsolete;
              description
                "FastEthernet IEEE 802.3";
              type string;
            }
            leaf GigabitEthernet {
              status obsolete;
              description
                "GigabitEthernet IEEE 802.3z";
              type string;
            }
            leaf FiveGigabitEthernet {
              status obsolete;
              description
                "Five GigabitEthernet ";
              type string;
            }
            leaf AppGigabitEthernet {
              status obsolete;
              description
                "App-hosting Gigabit Ethernet IEEE 802.3z";
              type string;
            }
            leaf TwentyFiveGigE {
              status obsolete;
              description
                "Twenty Five GigabitEthernet ";
              type string;
            }
            leaf TwoGigabitEthernet {
              status obsolete;
              description
                "Two GigabitEthernet ";
              type string;
            }
            leaf FortyGigabitEthernet {
              status obsolete;
              description
                "Forty GigabitEthernet ";
              type string;
            }
            leaf HundredGigE {
              status obsolete;
              description
                "Hundred GigabitEthernet";
              type string;
            }
            leaf LISP {
              status obsolete;
              description
                "Locator/ID Separation Protocol Virtual Interface";
              type string;
            }
            container LISP-subinterface {
              status obsolete;
              description
                "Locator/ID Separation Protocol Virtual Interface";
              leaf LISP {
                status obsolete;
                type string {
                  pattern '[0-9]*(. ?[1-9][0-9]*)*';
                }
              }
            }
            leaf Loopback {
              status obsolete;
              description
                "Loopback interface";
              type uint32;
            }
            leaf Multilink {
              status obsolete;
              description
                "Multilink-group interface";
              type uint16;
            }
            leaf nve {
              status obsolete;
              description
                "Network virtualization endpoint interface";
              type uint16;
            }
            leaf overlay {
              status obsolete;
              description
                "Overlay interface";
              type uint16;
            }
            leaf Port-channel {
              status obsolete;
              description
                "Ethernet Channel of interfaces";
              type uint32;
            }
            container Port-channel-subinterface {
              status obsolete;
              leaf Port-channel {
                status obsolete;
                type string;
              }
            }
            leaf pseudowire {
              status obsolete;
              description
                "Pseudowire Interface";
              type uint32;
            }
            leaf SM {
              status obsolete;
              description
                "SM Interface";
              type string;
            }
            leaf Cellular {
              status obsolete;
              description
                "Cellular Interface";
              type string;
            }
            leaf Dialer {
              status obsolete;
              description
                "Dialer Interface";
              type string;
            }
            leaf Serial {
              status obsolete;
              description
                "Serial interface";
              type string;
            }
            leaf TenGigabitEthernet {
              status obsolete;
              description
                "Ten Gigabit Ethernet";
              type string;
            }
            leaf Tunnel {
              status obsolete;
              description
                "Tunnel interface";
              type uint32;
            }
            leaf Virtual-Template {
              status obsolete;
              description
                "Virtual Template interface";
              type uint16;
            }
            leaf Vlan {
              status obsolete;
              description
                "Iosxr Vlans";
              type uint16;
            }
            leaf VirtualPortGroup {
              status obsolete;
              description
                "Virtual Port Group";
              type uint16;
            }
            leaf vasileft {
              status obsolete;
              description
                "vasileft";
              type uint16;
            }
            leaf vasiright {
              status obsolete;
              description
                "vasiright";
              type uint16;
            }
            leaf BD-VIF {
              status obsolete;
              description
                "Bridge-Domain Virtual IP interface";
              type string;
            }
          }
        }
      }
    }
  }

  grouping address-family-distribute-list-with-interface-grouping {
    container with-interface {
      list accesslist {
        key "acl in-out interface";
        leaf acl {
          description
            "Access-list number or name";
          mandatory true;
          type union {
            type uint16 {
              range "1..199";
            }
            type uint16 {
              range "1300..1999";
            }
            type string {
              pattern '[a-zA-Z].*';
            }
          }
        }
        leaf in-out {
          description
            "Filter incoming or out-going update";
          mandatory true;
          type ios-types:access-list-in-out-type;
        }
        leaf interface {
          description
            "Interface name";
          mandatory true;
          must '/ios:native/ios:interface/*[concat(local-name(.), ios:name) = current()]';
          type string;
        }
      }
      list prefix-gateway-name {
        key "prefix-gateway name in-out interface";
        leaf prefix-gateway {
          type enumeration {
            enum prefix;
            enum gateway;
          }
        }
        leaf name {
          description
            "Prefix-list name";
          type string;
        }
        leaf in-out {
          description
            "Filter incoming or out-going update";
          type ios-types:access-list-in-out-type;
        }
        leaf interface {
          description
            "Interface name";
          must '/ios:native/ios:interface/*[concat(local-name(.), ios:name) = current()]';
          type string;
        }
      }
    }
  }

  grouping evpn-rewrite-rt-grouping {
    leaf rewrite-evpn-rt-asn {
      description
        "Enable rewrite RT in the BGP EVPN address-family";
      type empty;
    }
  }

  grouping address-family-l2vpn-import-grouping {
    container import {
      description
        "Configure path import";
      container vpnv4 {
        leaf unicast {
          type empty;
        }
        leaf re-originate {
          type empty;
        }
      }
      container vpnv6 {
        leaf unicast {
          type empty;
        }
        leaf re-originate {
          description
            "Imported path with RT re-originate";
          type empty;
        }
      }
    }
  }

  grouping address-family-vpnv4-import-grouping {
    container import {
      description
        "Configure path import";
      container l2vpn {
        description
          "Configure EVPN to VPN path import";
        leaf evpn {
          type empty;
        }
        leaf re-originate {
          type empty;
        }
        leaf stitching-rt {
          when '../evpn and ../re-originate';
          type empty;
        }
      }
      container nhrp {
        description
          "Configure NHRP to VPN path import";
        presence "true";
        leaf route-map {
          description
            "Route-map to filter the prefixes";
          type string;
        }
      }
    }
  }

  grouping address-family-vpnv6-import-grouping {
    container import {
      description
        "Configure path import";
      container l2vpn {
        description
          "Configure EVPN to VPN path import";
        leaf evpn {
          type empty;
        }
        leaf re-originate {
          type empty;
        }
        leaf stitching-rt {
          when '../evpn and ../re-originate';
          type empty;
        }
      }
    }
  }

  grouping address-family-vrf-import-grouping {
    container import {
      description
        "Configure path import";
      container path {
        description
          "Path selection and path limit";
        leaf limit {
          description
            "Per net imported path limit";
          type uint8 {
            range "2..255";
          }
        }
        container selection {
          description
            "Path selection policy";
          leaf all {
            description
              "Import all available paths";
            type empty;
          }
        }
      }
      container vpnv4 {
        status obsolete;
        description
          "(OBSOLETE)";
        leaf unicast {
          status obsolete;
          type empty;
        }
        leaf re-originate {
          status obsolete;
          description
            "(OBSOLETE)";
          type empty;
        }
      }
      container vpnv6 {
        status obsolete;
        leaf unicast {
          status obsolete;
          description
            "(OBSOLETE)";
          type empty;
        }
        leaf re-originate {
          status obsolete;
          description
            "Imported path with RT re-originate (OBSOLETE)";
          type empty;
        }
      }
      container l2vpn {
        status obsolete;
        description
          "Configure EVPN to VPN path import (OBSOLETE)";
        leaf evpn {
          status obsolete;
          description
            "OBSOLETE";
          type empty;
        }
        leaf re-originate {
          status obsolete;
          description
            "OBSOLETE";
          type empty;
        }
      }
    }
  }

  grouping address-family-maximum-paths-grouping {
    container maximum-paths {
      description
        "Forward packets over multiple paths";
      leaf ebgp {
        description
          "eBGP-multipath";
        type uint16 {
          range "1..32";
        }
      }
      leaf eibgp {
        description
          "Both eBGP and iBGP paths as multipath";
        type uint16 {
          range "1..32";
        }
      }
      container ibgp {
        description
          "iBGP-multipath";
        choice ibgp-choice {
          leaf unequal-cost {
            description
              "Perform un-equal cost multipath selection";
            type uint16 {
              range "1..32";
            }
          }
          leaf max {
            type uint16 {
              range "1..32";
            }
          }
        }
      }
      must 'not(ebgp and eibgp) and not(eibgp and (ibgp/unequal-cost or ibgp/max))' {
        error-message "eibgp cannot be configured with ebgp or ibgp maximum-paths";
      }
    }
  }

  grouping address-family-ipv4-maximum-paths-grouping {
    container maximum-paths {
      description
        "Forward packets over multiple paths";
      leaf ebgp {
        description
          "eBGP-multipath";
        type uint16 {
          range "1..32";
        }
      }
      leaf eibgp {
        description
          "Both eBGP and iBGP paths as multipath";
        type uint16 {
          range "1..32";
        }
      }
      leaf ibgp-leaf {
        description
          "iBGP-multipath";
        type uint16 {
          range "1..32";
        }
      }
      container ibgp {
        status obsolete;
        description
          "iBGP-multipath (OBSOLETE)";
        choice ibgp-choice {
          status obsolete;
          leaf unequal-cost {
            status obsolete;
            description
              "Perform un-equal cost multipath selection (OBSOLETE)";
            type uint16 {
              range "1..32";
            }
          }
          leaf max {
            status obsolete;
            type uint16 {
              range "1..32";
            }
          }
        }
      }
      must 'not(ebgp and eibgp) and not(eibgp and ibgp-leaf)' {
        error-message "eibgp cannot be configured with ebgp or ibgp maximum-paths";
      }
    }
  }

  grouping address-family-ipv6-label-mode-grouping {
    container label {
      description
        "BGP LU Label config";
      container mode {
        description
          "BGP LU Label Mode config";
        choice mode-choice {
          leaf explicit-null {
            description
              "Locally Connected Route Explicit-null";
            type empty;
          }
          leaf all-explicit-null {
            description
              "All Prefix Explicit-null";
            type empty;
          }
        }
      }
    }
  }

  grouping address-family-rtf-maximum-paths-grouping {
    container maximum-paths {
      description
        "Forward packets over multiple paths";
      leaf external-rtfilter {
        description
          "VPN prefix maximum number of multipaths on external RT-Filter peers";
        default "1";
        type uint16 {
          range "1..32";
        }
      }
    }
  }

  grouping address-family-vpnv4-maximum-paths-grouping {
    container maximum-paths {
      description
        "Forward packets over multiple paths";
      leaf ebgp {
        type uint16 {
          range "1..32";
        }
      }
    }
  }

  grouping address-family-maximum-paths-ebgp-grouping {
    container maximum-paths {
      description
        "Forward packets over multiple paths";
      leaf ebgp {
        description
          "eBGP-multipath";
        type uint16 {
          range "1..32";
        }
      }
      leaf eibgp {
        status obsolete;
        description
          "Both eBGP and iBGP paths as multipath";
        type uint16 {
          range "1..32";
        }
      }
      container ibgp {
        status obsolete;
        description
          "iBGP-multipath";
        choice ibgp-choice {
          status obsolete;
          leaf unequal-cost {
            status obsolete;
            description
              "Perform un-equal cost multipath selection";
            type uint16 {
              range "1..32";
            }
          }
          leaf max {
            status obsolete;
            type uint16 {
              range "1..32";
            }
          }
        }
      }
    }
  }

  grouping address-family-link-state-domain-distinguisher-grouping {
    container domain-distinguisher {
      description
        "Configure BGP Domain distinguisher";
      presence "BGP Domain distinguisher";
      leaf as-num {
        type ios-types:bgp-as-number-type;
        mandatory true;
        description
          "AS number";
      }
      leaf lsid-choice {
        mandatory true;
        type union {
          type uint32 {
            range "1..2147483647";
          }
          type inet:ipv4-address;
        }
      }
    }
  }

  grouping address-family-link-state-propagate-aspath-grouping {
    leaf propagate-aspath {
      description
        "Propagate AS Path";
      type empty;
    }
  }

  grouping address-family-ipv4-network-grouping {
    container network {
      list with-mask {
        description
          "Specify a network to announce via BGP";
        key "number mask";
        leaf number {
          type inet:ipv4-address;
        }
        leaf mask {
          description
            "Network mask";
          type inet:ipv4-address;
        }
        leaf route-map {
          description
            "Route-map to modify the attributes";
          type string;
        }
        leaf backdoor {
          description
            "Specify a BGP backdoor route";
          type empty;
        }
      }
      list no-mask {
        description
          "Specify a network to announce via BGP";
        key "number";
        leaf number {
          type inet:ipv4-address;
        }
        leaf route-map {
          description
            "Route-map to modify the attributes";
          type string;
        }
        leaf backdoor {
          description
            "Specify a BGP backdoor route";
          type empty;
        }
      }
    }
  }

  grouping address-family-vrf-ipv4-network-grouping {
    container network {
      list with-mask {
        description
          "Specify a network to announce via BGP";
        key "number mask";
        leaf number {
          type inet:ipv4-address;
        }
        leaf mask {
          description
            "Network mask";
          type inet:ipv4-address;
        }
        leaf route-map {
          description
            "Route-map to modify the attributes";
          type string;
        }
        choice network-option {
          leaf backdoor {
            description
              "Specify a BGP backdoor route";
            type empty;
          }
          leaf evpn {
            description
              "Advertise or export to EVPN address-family";
            type empty;
          }
        }
      }
      list no-mask {
        description
          "Specify a network to announce via BGP";
        key "number";
        leaf number {
          type inet:ipv4-address;
        }
        leaf route-map {
          description
            "Route-map to modify the attributes";
          type string;
        }
        choice network-option {
          leaf backdoor {
            description
              "Specify a BGP backdoor route";
            type empty;
          }
          leaf evpn {
            description
              "Advertise or export to EVPN address-family";
            type empty;
          }
        }
      }
    }
  }

  grouping address-family-nsap-network-grouping {
    list network {
      description
        "Specify a network to announce via BGP";
      key "number";
      leaf number {
        type inet:ipv4-address;
      }
      leaf route-map {
        description
          "Route-map to modify the attributes";
        type string;
      }
    }
  }

  grouping address-family-ipv6-network-grouping {
    list network {
      description
        "Specify a network to announce via BGP";
      key "number";
      leaf number {
        type ios-types:ipv6-prefix;
      }
      leaf route-map {
        description
          "Route-map to modify the attributes";
        type string;
      }
      leaf backdoor {
        description
          "Specify a BGP backdoor route";
        type empty;
      }
    }
  }

  grouping address-family-vrf-ipv6-network-grouping {
    list network {
      description
        "Specify a network to announce via BGP";
      key "number";
      leaf number {
        type ios-types:ipv6-prefix;
      }
      leaf route-map {
        description
          "Route-map to modify the attributes";
        type string;
      }
      leaf backdoor {
        description
          "Specify a BGP backdoor route";
        type empty;
      }
      leaf evpn {
        description
          "Advertise or export to EVPN address-family";
        type empty;
      }
    }
  }

  grouping address-family-propagate-aspath-grouping {
    leaf propagate-aspath {
      if-feature "ios-features:omp";
      description
        "BGP Propagate AS Path";
      type empty;
    }
    leaf propagate-community {
      if-feature "ios-features:omp";
      description
        "BGP Propagate Community";
      type empty;
    }
  }

  grouping address-family-redistribute-vrf-grouping {
    list vrf {
      description
        "Specify a source VRF";
      key "vrf-name";
      leaf vrf-name {
        description
          "Source VRF name";
        type union {
          type string;
          type enumeration {
            enum global;
          }
        }
      }
      container bgp {
        description
          "Border Gateway Protocol (BGP)";
        presence "true";
        leaf as-no {
          mandatory true;
          type ios-types:bgp-as-number-type;
        }
        uses redistribute-metric-route-map-v2-grouping;
      }
      container connected {
        description
          "Connected";
        presence "Connected";
        uses redistribute-metric-route-map-v2-grouping;
      }
      container eigrp {
        description
          "Enhanced Interior Gateway Routing Protocol (EIGRP)";
        leaf as-no {
          type uint16 {
            range "1..65535";
          }
        }
        uses metric-route-map-grouping;
      }
      list ospf {
        description
          "Open Shortest Path First (OSPF)";
        key "id";
        leaf id {
          type uint16 {
            range "1..65535";
          }
        }
        uses redistribute-ospf-non-vrf-grouping;
      }
      container static {
        presence "Static routes";
        description
          "Static routes";
        choice static-choice {
          container clns {
            description
              "Redistribution of OSI dynamic routes";
            presence "true";
            uses redistribute-metric-route-map-v2-grouping;
          }
          container ip {
            presence "true";
            uses redistribute-metric-route-map-v2-grouping;
          }
          container default {
            uses redistribute-metric-route-map-v2-grouping;
          }
        }
      }
    }
  }

  grouping address-family-redistribute-grouping {
    container redistribute {
      description
        "Redistribute information from another routing protocol";
      container application {
        description
          "Application";
        presence "true";
        list name {
          key "name";
          leaf name {
            description
              "WORD :: Route-map name";
            type string;
          }
          uses metric-route-map-grouping;
        }
      }
      container bgp {
        status obsolete;
        description
          "Border Gateway Protocol (BGP) (OBSOLETE)";
        leaf as-no {
          status obsolete;
          type ios-types:bgp-as-number-type;
        }
        uses metric-route-map-grouping-obsolete;
      }
      container connected {
        description
          "Connected";
        presence "Connected";
        uses redistribute-metric-route-map-v2-grouping;
      }
      container dvmrp {
        status obsolete;
        description
          "Redistribution of DVMRP into BGP IPv4 Multicast (OBSOLETE)";
        presence "Redistribution of DVMRP into BGP IPv4 Multicast";
        uses metric-route-map-grouping-obsolete;
      }
      container eigrp {
        description
          "Enhanced Interior Gateway Routing Protocol (EIGRP)";
        leaf as-no {
          type uint16 {
            range "1..65535";
          }
        }
        uses metric-route-map-grouping;
      }
      container isis {
        description
          "ISO IS-IS";
        presence "true";
        must '/ios:native/ios:router/ios-isis:isis' {
          error-message "Router isis must be configured before redistribute isis and deleted after redistribute isis";
        }
        uses redistribute-isis-grouping;
      }
      container isis-area-tag {
        description
          "ISO IS-IS area-tag";
        list isis {
          key "area-tag";
          leaf area-tag {
            type leafref {
              path "/ios:native/ios:router/ios-isis:isis-container/ios-isis:isis/ios-isis:area-tag";
            }
          }
          uses redistribute-isis-grouping;
        }
      }
      container lisp {
        description
          "Locator/ID Separation Protocol";
        presence "lisp";
        leaf include-connected {
          status obsolete;
          description
            "OBSOLETE";
          type empty;
        }
        uses redistribute-metric-route-map-v2-grouping;
      }
      container iso-igrp {
        description
          "IGRP for OSI networks";
        list iso-igrp-area {
          key "name";
          leaf name {
            type string;
          }
          uses route-map-metric-grouping;
        }
        container default {
          uses route-map-metric-grouping;
        }
      }
      container mobile {
        presence "Mobile routes";
        description
          "Mobile routes";
        uses redistribute-metric-route-map-v2-grouping;
      }
      container odr {
        presence "On Demand stub Routes";
        description
          "On Demand stub Routes";
        uses redistribute-metric-route-map-v2-grouping;
      }
      container omp {
        if-feature "ios-features:omp";
        description
          "Overlay Management Protocol (OMP)";
        presence "omp";
        uses redistribute-metric-route-map-v2-grouping;
      }
      container nat-route {
        if-feature "ios-features:sdwan";
        description
          "NAT Route";
        presence "NAT Route";
        leaf dia {
          description
            "Redistribute NAT Direct Internet Access routes";
          type empty;
        }
        leaf outside {
          description
            "Redistribute NAT outside routes";
          type empty;
        }
        uses metric-route-map-grouping;
      }
      list ospf {
        description
          "Open Shortest Path First (OSPF)";
        key "id";
        leaf id {
          type uint16 {
            range "1..65535";
          }
        }
        choice ospf-choice {
          list vrf {
            description
              "VPN Routing/Forwarding Instance";
            key "name";
            leaf name {
              must '/ios:native/ios:vrf/ios:definition[ios:name=current()] or /ios:native/ios:ip/ios:vrf[ios:name=current()]' {
                error-message "VRF must be created 1st, deleted last";
              }
              type string;
            }
            uses redistribute-ospf-non-vrf-grouping;
          }
          container non-vrf {
            uses redistribute-ospf-non-vrf-grouping;
          }
        }
      }
      list ospfv3 {
        description
          "OSPFv3";
        key "id";
        leaf id {
          type leafref {
            path "/ios:native/ios:router/ios-ospfv3:ospfv3/ios-ospfv3:id";
          }
        }
        uses redistribute-ospf-non-vrf-grouping;
      }
      container rip {
        presence "Routing Information Protocol (RIP)";
        description
          "Routing Information Protocol (RIP)";
        leaf name {
          description
            "User selected string identifying this process";
          type string;
        }
        uses redistribute-metric-route-map-v2-grouping;
      }
      container static {
        presence "Static routes";
        description
          "Static routes";
        choice static-choice {
          container clns {
            description
              "Redistribution of OSI dynamic routes";
            presence "true";
            uses route-map-metric-grouping;
          }
          container ip {
            presence "true";
            uses metric-route-map-grouping;
          }
          container default {
            uses metric-route-map-grouping;
          }
        }
      }
      uses address-family-redistribute-vrf-grouping;
    }
  }

  grouping address-family-redistribute-grouping-obsolete {
    container redistribute {
      status obsolete;
      description
        "Redistribute information from another routing protocol";
      container application {
        status obsolete;
        description
          "Application";
        presence "true";
        list name {
          status obsolete;
          key "name";
          leaf name {
            status obsolete;
            description
              "WORD :: Route-map name";
            type string;
          }
          uses metric-route-map-grouping-obsolete;
        }
      }
      container bgp {
        status obsolete;
        description
          "Border Gateway Protocol (BGP) (OBSOLETE)";
        leaf as-no {
          status obsolete;
          type ios-types:bgp-as-number-type;
        }
        uses metric-route-map-grouping-obsolete;
      }
      container connected {
        description
          "Connected";
        status obsolete;
        presence "Connected";
        uses metric-route-map-grouping-obsolete;
      }
      container dvmrp {
        status obsolete;
        description
          "Redistribution of DVMRP into BGP IPv4 Multicast (OBSOLETE)";
        presence "Redistribution of DVMRP into BGP IPv4 Multicast";
        uses metric-route-map-grouping-obsolete;
      }
      container eigrp {
        description
          "Enhanced Interior Gateway Routing Protocol (EIGRP)";
        status obsolete;
        leaf as-no {
          status obsolete;
          type uint16 {
            range "1..65535";
          }
        }
        uses metric-route-map-grouping-obsolete;
      }
      container isis {
        status obsolete;
        description
          "ISO IS-IS";
        presence "true";
        must '/ios:native/ios:router/ios-isis:isis' {
          error-message "Router isis must be configured before redistribute isis and deleted after redistribute isis";
        }
        choice osi-ip-choice {
          status obsolete;
          leaf ip {
            status obsolete;
            description
              "Redistribution of IP dynamic routes";
            type empty;
          }
          leaf clns {
            status obsolete;
            description
              "Redistribution of OSI dynamic routes";
            type empty;
          }
        }
        leaf routes {
          status obsolete;
          default "level-2";
          type enumeration {
            enum level-1;
            enum level-2;
            enum level-1-2;
          }
        }
        uses metric-route-map-grouping-obsolete;
      }
      container isis-area-tag {
        description
          "ISO IS-IS area-tag";
        status obsolete;
        list isis {
          status obsolete;
          key "area-tag";
          leaf area-tag {
            status obsolete;
            type leafref {
              path "/ios:native/ios:router/ios-isis:isis-container/ios-isis:isis/ios-isis:area-tag";
            }
          }
          choice osi-ip-choice {
            status obsolete;
            leaf ip {
              status obsolete;
              description
                "Redistribution of IP dynamic routes";
              type empty;
            }
            leaf clns {
              status obsolete;
              description
                "Redistribution of OSI dynamic routes";
              type empty;
            }
          }
          leaf routes {
            status obsolete;
            default "level-2";
            type enumeration {
              enum level-1;
              enum level-2;
              enum level-1-2;
            }
          }
          uses metric-route-map-grouping-obsolete;
        }
      }
      container lisp {
        description
          "Locator/ID Separation Protocol";
        status obsolete;
        presence "lisp";
        leaf include-connected {
          status obsolete;
          description
            "OBSOLETE";
          type empty;
        }
        uses metric-route-map-grouping-obsolete;
      }
      container iso-igrp {
        status obsolete;
        description
          "IGRP for OSI networks";
        list iso-igrp-area {
          status obsolete;
          key "name";
          leaf name {
            status obsolete;
            type string;
          }
          uses metric-route-map-grouping-obsolete;
        }
        container default {
          status obsolete;
          uses metric-route-map-grouping-obsolete;
        }
      }
      container mobile {
        status obsolete;
        presence "Mobile routes";
        description
          "Mobile routes";
        uses metric-route-map-grouping-obsolete;
      }
      container odr {
        presence "On Demand stub Routes";
        status obsolete;
        description
          "On Demand stub Routes";
        uses metric-route-map-grouping-obsolete;
      }
      container omp {
        if-feature "ios-features:omp";
        description
          "Overlay Management Protocol (OMP)";
        status obsolete;
        presence "omp";
        uses metric-route-map-grouping-obsolete;
      }
      container nat-route {
        if-feature "ios-features:sdwan";
        description
          "NAT Route";
        status obsolete;
        leaf dia {
          status obsolete;
          description
            "Redistribute NAT Direct Internet Access routes";
          type empty;
        }
        leaf outside {
          status obsolete;
          description
            "Redistribute NAT outside routes";
          type empty;
        }
        uses metric-route-map-grouping-obsolete;
      }
      list ospf {
        description
          "Open Shortest Path First (OSPF)";
        status obsolete;
        key "id";
        leaf id {
          status obsolete;
          type uint16 {
            range "1..65535";
          }
        }
        choice ospf-choice {
          status obsolete;
          list vrf {
            description
              "VPN Routing/Forwarding Instance";
            status obsolete;
            key "name";
            leaf name {
              status obsolete;
              must '/ios:native/ios:vrf/ios:definition[ios:name=current()] or /ios:native/ios:ip/ios:vrf[ios:name=current()]' {
                error-message "VRF must be created 1st, deleted last";
              }
              type string;
            }
            container match {
              status obsolete;
              leaf internal {
                status obsolete;
                description
                  "Redistribute OSPF internal routes";
                type empty;
              }
              leaf external {
                status obsolete;
                description
                  "Redistribute OSPF external routes";
                type ios-types:redist-ospf-external-type;
              }
              leaf external2 {
                status obsolete;
                description
                  "Redistribute OSPF external routes";
                type ios-types:redist-ospf-external-type;
              }
              leaf nssa-external {
                status obsolete;
                description
                  "Redistribute OSPF NSSA external routes";
                type ios-types:redist-ospf-external-type;
              }
            }
            uses metric-route-map-grouping-obsolete;
          }
          container non-vrf {
            status obsolete;
            container match {
              status obsolete;
              leaf internal {
                status obsolete;
                description
                  "Redistribute OSPF internal routes";
                type empty;
              }
              leaf external {
                status obsolete;
                description
                  "Redistribute OSPF external routes";
                type ios-types:redist-ospf-external-type;
              }
              leaf external2 {
                status obsolete;
                description
                  "Redistribute OSPF external routes";
                type ios-types:redist-ospf-external-type;
              }
              leaf nssa-external {
                status obsolete;
                description
                  "Redistribute OSPF NSSA external routes";
                type ios-types:redist-ospf-external-type;
              }
            }
            uses metric-route-map-grouping-obsolete;
          }
        }
      }
      list ospfv3 {
        description
          "OSPFv3";
        status obsolete;
        key "id";
        leaf id {
          status obsolete;
          type leafref {
            path "/ios:native/ios:router/ios-ospfv3:ospfv3/ios-ospfv3:id";
          }
        }
        container match {
          status obsolete;
          leaf internal {
            status obsolete;
            description
              "Redistribute OSPF internal routes";
            type empty;
          }
          leaf external {
            status obsolete;
            description
              "Redistribute OSPF external routes";
            type ios-types:redist-ospf-external-type;
          }
          leaf external2 {
            status obsolete;
            description
              "Redistribute OSPF external routes";
            type ios-types:redist-ospf-external-type;
          }
          leaf nssa-external {
            status obsolete;
            description
              "Redistribute OSPF NSSA external routes";
            type ios-types:redist-ospf-external-type;
          }
        }
        uses metric-route-map-grouping-obsolete;
      }
      container rip {
        presence "Routing Information Protocol (RIP)";
        status obsolete;
        description
          "Routing Information Protocol (RIP)";
        leaf name {
          description
            "User selected string identifying this process";
          status obsolete;
          type string;
        }
        uses metric-route-map-grouping-obsolete;
      }
      container static {
        presence "Static routes";
        status obsolete;
        description
          "Static routes";
        choice static-choice {
          status obsolete;
          container clns {
            status obsolete;
            description
              "Redistribution of OSI dynamic routes";
            presence "true";
            uses metric-route-map-grouping-obsolete;
          }
          container ip {
            status obsolete;
            presence "true";
            uses metric-route-map-grouping-obsolete;
          }
          container default {
            status obsolete;
            uses metric-route-map-grouping-obsolete;
          }
        }
      }
    }
  }

  grouping address-family-vrf-redistribute-grouping {
    container redistribute-vrf {
      description
        "Redistribute information from another routing protocol";
      uses redistribute-application-grouping;
      uses redistribute-connected-grouping;
      uses redistribute-eigrp-grouping;
      uses redist-isis-grouping;
      uses redistribute-lisp-grouping;
      uses redistribute-mobile-grouping;
      uses redistribute-nat-route-grouping;
      uses redistribute-odr-grouping;
      uses redistribute-omp-grouping;
      uses redistribute-ospf-grouping;
      uses redistribute-ospfv3-grouping;
      uses redistribute-rip-grouping;
      uses redistribute-static-grouping;
      uses address-family-redistribute-vrf-grouping;
    }
  }

  grouping address-family-v6-redistribute-grouping {
    container redistribute-v6 {
      description
        "Redistribute information from another routing protocol";
      uses redistribute-application-v6-grouping;
      uses redistribute-connected-grouping;
      uses redistribute-eigrp-v6-grouping;
      uses redistribute-isis-v6-grouping;
      uses redistribute-lisp-v6-grouping;
      uses redistribute-omp-grouping;
      uses redistribute-ospf-v6-grouping;
      uses redistribute-rip-v6-grouping;
      uses redistribute-static-v6-grouping;
    }
  }

  grouping address-family-v6-redistribute-grouping-obsolete {
    container redistribute-v6 {
      status obsolete;
      description
        "Redistribute information from another routing protocol (OBSOLETE)";
      container application {
        status obsolete;
        description
          "Application (OBSOLETE)";
        presence "true";
        uses redistribute-include-connected-grouping-obsolete;
        uses metric-route-map-grouping-obsolete;
      }
      container connected {
        status obsolete;
        description
          "Connected (OBSOLETE)";
        presence "Connected";
        uses metric-route-map-grouping-obsolete;
      }
      container eigrp {
        status obsolete;
        description
          "Enhanced Interior Gateway Routing Protocol (EIGRP)  (OBSOLETE)";
        leaf as-no {
          status obsolete;
          type uint16 {
            range "1..65535";
          }
        }
        uses redistribute-include-connected-grouping-obsolete;
        uses metric-route-map-grouping-obsolete;
      }
      container isis {
        status obsolete;
        description
          "ISO IS-IS (OBSOLETE)";
        presence "true";
        must '/ios:native/ios:router/ios-isis:isis' {
          error-message "Router isis must be configured before redistribute isis and deleted after redistribute isis";
        }
        uses redistribute-include-connected-grouping-obsolete;
        uses metric-route-map-grouping-obsolete;
      }
      container isis-area-tag {
        status obsolete;
        description
          "ISO IS-IS area-tag (OBSOLETE)";
        list isis {
          status obsolete;
          key "area-tag";
          leaf area-tag {
            status obsolete;
            type leafref {
              path "/ios:native/ios:router/ios-isis:isis-container/ios-isis:isis/ios-isis:area-tag";
            }
          }
          uses redistribute-include-connected-grouping-obsolete;
          uses metric-route-map-grouping-obsolete;
        }
      }
      container lisp {
        status obsolete;
        description
          "Locator/ID Separation Protocol (OBSOLETE)";
        presence "lisp";
        uses redistribute-include-connected-grouping-obsolete;
        uses metric-route-map-grouping-obsolete;
      }
      container omp {
        status obsolete;
        if-feature "ios-features:omp";
        description
          "Overlay Management Protocol (OMP) (OBSOLETE)";
        presence "omp";
        uses metric-route-map-grouping-obsolete;
      }
      list ospf {
        status obsolete;
        description
          "Open Shortest Path First (OSPF) (OBSOLETE)";
        key "id";
        leaf id {
          status obsolete;
          type uint16 {
            range "1..65535";
          }
        }
        container match {
          status obsolete;
          leaf internal {
            status obsolete;
            description
              "Redistribute OSPF internal routes";
            type empty;
          }
          leaf external {
            status obsolete;
            description
              "Redistribute OSPF external routes";
            type ios-types:redist-ospf-external-type;
          }
          leaf external2 {
            status obsolete;
            description
              "Redistribute OSPF external routes";
            type ios-types:redist-ospf-external-type;
          }
          leaf nssa-external {
            status obsolete;
            description
              "Redistribute OSPF NSSA external routes";
            type ios-types:redist-ospf-external-type;
          }
        }
        uses redistribute-include-connected-grouping-obsolete;
        uses metric-route-map-grouping-obsolete;
      }
      container rip {
        status obsolete;
        presence "Routing Information Protocol (RIP)";
        description
          "Routing Information Protocol (RIP) (OBSOLETE)";
        leaf name {
          status obsolete;
          description
            "User selected string identifying this process (OBSOLETE)";
          type string;
        }
        uses redistribute-include-connected-grouping-obsolete;
        uses metric-route-map-grouping-obsolete;
      }
      container static {
        status obsolete;
        presence "Static routes (OBSOLETE)";
        description
          "Static routes";
        uses metric-route-map-grouping-obsolete;
      }
    }
  }

  grouping redistribute-application-grouping {
    container application {
      description
        "Application";
      presence "true";
      list name {
        key "name";
        leaf name {
          description
            "WORD :: Route-map name";
          type string;
        }
        uses metric-route-map-grouping;
      }
    }
  }

  grouping redistribute-application-v6-grouping {
    container application {
      description
        "Application";
      presence "true";
      uses redistribute-include-connected-v2-grouping;
      uses redistribute-metric-route-map-v2-grouping;
    }
  }

  grouping redistribute-connected-grouping {
    container connected {
      description
        "Connected";
      presence "Connected";
      uses redistribute-metric-route-map-v2-grouping;
    }
  }

  grouping redistribute-dvmrp-grouping {
    container dvmrp {
      description
        "Redistribution of DVMRP into BGP IPv4 Multicast";
      presence "Redistribution of DVMRP into BGP IPv4 Multicast";
      uses redistribute-metric-route-map-v2-grouping;
    }
  }

  grouping redistribute-eigrp-grouping {
    container eigrp {
      description
        "Enhanced Interior Gateway Routing Protocol (EIGRP)";
      leaf as-no {
        type uint16 {
          range "1..65535";
        }
      }
      uses metric-route-map-grouping;
    }
  }

  grouping redistribute-eigrp-v6-grouping {
    container eigrp {
      description
        "Enhanced Interior Gateway Routing Protocol (EIGRP)";
      leaf as-no {
        type uint16 {
          range "1..65535";
        }
      }
      uses redistribute-include-connected-grouping;
      uses metric-route-map-grouping;
    }
  }

  grouping redist-isis-grouping {
    container isis {
      description
        "ISO IS-IS";
      presence "true";
      must '/ios:native/ios:router/ios-isis:isis' {
        error-message "Router isis must be configured before redistribute isis and deleted after redistribute isis";
      }
      uses redistribute-isis-grouping;
    }
    container isis-area-tag {
      description
        "ISO IS-IS area-tag";
      list isis {
        key "area-tag";
        leaf area-tag {
          type leafref {
            path "/ios:native/ios:router/ios-isis:isis-container/ios-isis:isis/ios-isis:area-tag";
          }
        }
        uses redistribute-isis-grouping;
      }
    }
  }

  grouping redistribute-isis-v6-grouping {
    container isis {
      description
        "ISO IS-IS";
      presence "true";
      must '/ios:native/ios:router/ios-isis:isis' {
        error-message "Router isis must be configured before redistribute isis and deleted after redistribute isis";
      }
      uses redistribute-isis-routes-grouping;
      uses redistribute-include-connected-grouping;
      uses metric-route-map-grouping;
    }
    container isis-area-tag {
      description
        "ISO IS-IS area-tag";
      list isis {
        key "area-tag";
        leaf area-tag {
          type leafref {
            path "/ios:native/ios:router/ios-isis:isis-container/ios-isis:isis/ios-isis:area-tag";
          }
        }
        uses redistribute-isis-routes-grouping;
        uses redistribute-include-connected-grouping;
        uses metric-route-map-grouping;
      }
    }
  }

  grouping redistribute-lisp-grouping {
    container lisp {
      description
        "Locator/ID Separation Protocol";
      presence "lisp";
      uses redistribute-metric-route-map-v2-grouping;
    }
  }

  grouping redistribute-lisp-v6-grouping {
    container lisp {
      description
        "Locator/ID Separation Protocol";
      presence "lisp";
      uses redistribute-include-connected-v2-grouping;
      uses redistribute-metric-route-map-v2-grouping;
    }
  }

  grouping redistribute-iso-igrp-grouping {
    container iso-igrp {
      description
        "IGRP for OSI networks";
      list iso-igrp-area {
        key "name";
        leaf name {
          type string;
        }
        uses redistribute-metric-route-map-v2-grouping;
      }
      container default {
        uses redistribute-metric-route-map-v2-grouping;
      }
    }
  }

  grouping redistribute-mobile-grouping {
    container mobile {
      presence "Mobile routes";
      description
        "Mobile routes";
      uses redistribute-metric-route-map-v2-grouping;
    }
  }

  grouping redistribute-odr-grouping {
    container odr {
      presence "On Demand stub Routes";
      description
        "On Demand stub Routes";
      uses redistribute-metric-route-map-v2-grouping;
    }
  }

  grouping redistribute-omp-grouping {
    container omp {
      if-feature "ios-features:omp";
      description
        "Overlay Management Protocol (OMP)";
      presence "omp";
      uses redistribute-metric-route-map-v2-grouping;
    }
  }

  grouping redistribute-nat-route-grouping {
    container nat-route {
      if-feature "ios-features:sdwan";
      description
        "NAT Route";
      presence "NAT Route";
      leaf dia {
        description
          "Redistribute NAT Direct Internet Access routes";
        type empty;
      }
      leaf outside {
        description
          "Redistribute NAT outside routes";
        type empty;
      }
      uses metric-route-map-grouping;
    }
  }

  grouping redistribute-ospf-grouping {
    list ospf {
      description
        "Open Shortest Path First (OSPF)";
      key "id";
      leaf id {
        type uint16 {
          range "1..65535";
        }
      }
      choice ospf-choice {
        list vrf {
          description
            "VPN Routing/Forwarding Instance";
          key "name";
          leaf name {
            must '/ios:native/ios:vrf/ios:definition[ios:name=current()] or /ios:native/ios:ip/ios:vrf[ios:name=current()]' {
              error-message "VRF must be created 1st, deleted last";
            }
            type string;
          }
          uses redistribute-ospf-non-vrf-grouping;
        }
        container non-vrf {
          uses redistribute-ospf-non-vrf-grouping;
        }
      }
    }
  }

  grouping redistribute-ospf-v6-grouping {
    list ospf {
      description
        "Open Shortest Path First (OSPF)";
      key "id";
      leaf id {
        type uint16 {
          range "1..65535";
        }
      }
      uses ospf-v6-grouping;
    }
  }

  grouping redistribute-ospfv3-grouping {
    list ospfv3 {
      description
        "OSPFv3";
      key "id";
      leaf id {
        type leafref {
          path "/ios:native/ios:router/ios-ospfv3:ospfv3/ios-ospfv3:id";
        }
      }
      uses redistribute-ospf-non-vrf-grouping;
    }
  }

  grouping redistribute-rip-grouping {
    container rip {
      presence "Routing Information Protocol (RIP)";
      description
        "Routing Information Protocol (RIP)";
      leaf name {
        description
          "User selected string identifying this process (OBSOLETE)";
        status obsolete;
        type string;
      }
      uses redistribute-metric-route-map-v2-grouping;
    }
  }

  grouping redistribute-rip-v6-grouping {
    container rip {
      description
        "Routing Information Protocol (RIP)";
      leaf name {
        description
          "User selected string identifying this process";
        type string;
      }
      uses redistribute-include-connected-v2-grouping {
        when 'name';
      }
      uses redistribute-metric-route-map-v2-grouping {
        when 'name';
      }
    }
  }

  grouping redistribute-static-grouping {
    container static {
      presence "Static routes";
      description
        "Static routes";
      choice static-choice {
        container clns {
          description
            "Redistribution of OSI dynamic routes";
          presence "true";
          uses metric-route-map-grouping;
        }
        container ip {
          presence "true";
          uses metric-route-map-grouping;
        }
        container default {
          uses metric-route-map-grouping;
        }
      }
    }
  }

  grouping redistribute-static-v6-grouping {
    container static {
      presence "Static routes";
      description
        "Static routes";
      uses redistribute-metric-route-map-v2-grouping;
    }
  }

  grouping metric-route-map-grouping {
    leaf metric {
      description
        "Metric for redistributed routes";
      type uint32 {
        range "0..4294967295";
      }
    }
    leaf route-map {
      description
        "Route map reference";
      type string;
    }
  }

  grouping redistribute-metric-route-map-v2-grouping {
    leaf metric {
      description
        "Metric for redistributed routes";
      default "0";
      type uint32 {
        range "0..4294967295";
      }
    }
    leaf route-map {
      description
        "Route map reference";
      type string;
    }
  }

  grouping metric-route-map-grouping-obsolete {
    leaf metric {
      status obsolete;
      description
        "Metric for redistributed routes";
      type uint32 {
        range "0..4294967295";
      }
    }
    leaf route-map {
      status obsolete;
      description
        "Route map reference";
      type string;
    }
  }

  grouping route-map-metric-grouping {
    leaf route-map {
      description
        "Route map reference";
      type string;
    }
    leaf metric {
      description
        "Metric for redistributed routes";
      type uint32 {
        range "0..4294967295";
      }
    }
  }

  grouping redistribute-isis-grouping {
    choice osi-ip-choice {
      leaf ip {
        description
          "Redistribution of IP dynamic routes";
        type empty;
      }
      leaf clns {
        description
          "Redistribution of OSI dynamic routes";
        type empty;
      }
    }
    uses redistribute-isis-routes-grouping;
    uses metric-route-map-grouping;
  }

  grouping redistribute-isis-routes-grouping {
    leaf routes {
      default "level-2";
      type enumeration {
        enum level-1;
        enum level-2;
        enum level-1-2;
      }
    }
  }

  grouping redistribute-ospf-non-vrf-grouping {
    container match {
      leaf internal {
        description
          "Redistribute OSPF internal routes";
        type empty;
      }
      leaf external {
        description
          "Redistribute OSPF external routes";
        type ios-types:redist-ospf-external-type;
      }
      leaf external2 {
        description
          "Redistribute OSPF external routes";
        type ios-types:redist-ospf-external-type;
      }
      leaf nssa-external {
        description
          "Redistribute OSPF NSSA external routes";
        type ios-types:redist-ospf-external-type;
      }
    }
    uses redistribute-metric-route-map-v2-grouping;
  }

  grouping ospf-v6-grouping {
    container match {
      leaf internal {
        description
          "Redistribute OSPF internal routes";
        type empty;
      }
      leaf external {
        description
          "Redistribute OSPF external routes";
        type ios-types:redist-ospf-external-type;
      }
      leaf external2 {
        description
          "Redistribute OSPF external routes";
        type ios-types:redist-ospf-external-type;
      }
      leaf nssa-external {
        description
          "Redistribute OSPF NSSA external routes";
        type ios-types:redist-ospf-external-type;
      }
    }
    uses redistribute-include-connected-v2-grouping;
    uses redistribute-metric-route-map-v2-grouping;
  }

  grouping redistribute-include-connected-grouping {
    leaf include-connected {
      description
        "Include connected";
      type empty;
    }
  }

  grouping redistribute-include-connected-v2-grouping {
    leaf include-connected {
      description
        "Include connected";
      type empty;
    }
  }

  grouping redistribute-include-connected-grouping-obsolete {
    leaf include-connected {
      status obsolete;
      description
        "Include connected";
      type empty;
    }
  }

  grouping address-family-segment-routing-grouping {
    container segment-routing {
      description
        "segment-routing";
      leaf mpls {
        description
          "mpls";
        type empty;
      }
    }
  }

  grouping address-family-snmp-grouping {
    container snmp {
      description
        "Modify snmp parameters";
      container context {
        description
          "Configure a SNMP context";
        list context_word {
          key "context_word";
          leaf context_word {
            description
              "Context Name";
            type string;
          }
        }
      }
    }
  }

  grouping address-family-synchronization-grouping {
    leaf synchronization {
      description
        "Perform IGP synchronization";
      type empty;
    }
  }

  grouping address-family-table-map-grouping {
    container table-map {
      description
        "Map external entry attributes into routing table";
      leaf name {
        description
          "WORD :: Route-map name";
        type string;
      }
      leaf filter {
        type empty;
      }
    }
  }

  grouping global-neighbor {
    uses neighbor-remote-as-grouping {
      refine "remote-as";
    }
    uses global-neighbor-inherit-grouping;
    uses neighbor-peer-group-grouping {
      refine "peer-group/peer-group-name" {
        must '(/ios:native/ios:router/ios-bgp:bgp/peer-group/neighbor[id=current()]/peer-group)' {
          error-message "The peer-group should be configured before attaching with the neighbor";
        }
      }
    }
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses neighbor-local-as-grouping;
    uses neighbor-log-neighbor-changes-grouping;
    uses neighbor-password-grouping;
    uses neighbor-ao-grouping;
    uses neighbor-path-attribute-grouping;
    uses neighbor-shutdown-grouping;
    uses neighbor-timers-grouping;
    uses neighbor-transport-grouping;
    uses neighbor-ttl-security-grouping;
    uses neighbor-update-grouping;
    uses neighbor-update-source-grouping;
    uses neighbor-version-grouping;
  }

  grouping global-peer-group {
    uses peer-group-peer-group-grouping;
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses peer-group-inherit-grouping;
    uses neighbor-peer-group-local-as-grouping;
    uses neighbor-log-neighbor-changes-grouping;
    uses neighbor-password-grouping;
    uses neighbor-ao-grouping;
    uses neighbor-path-attribute-grouping;
    uses neighbor-remote-as-grouping;
    uses neighbor-shutdown-grouping;
    uses neighbor-timers-grouping;
    uses neighbor-transport-grouping;
    uses neighbor-ttl-security-grouping;
    uses neighbor-update-grouping;
    uses neighbor-update-source-grouping;
    uses neighbor-version-grouping;
  }

  grouping ipv4-unicast-neighbor {
    uses neighbor-activate-grouping;
    uses neighbor-additional-paths-grouping;
    uses neighbor-advertise-grouping;
    uses neighbor-advertise-map-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-default-originate-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping {
      refine "route-reflector-client" {
        must 'not(../advertise/best-external)' {
          error-message "route-reflector-client and advertise/best-external cannot be configured at the same time";
        }
      }
    }
    uses neighbor-send-community-grouping;
    uses neighbor-send-label-grouping;
    uses neighbor-slow-peer-grouping;
    uses neighbor-soft-reconfiguration-grouping;
    uses neighbor-soo-grouping;
    uses neighbor-translate-update-grouping;
    uses neighbor-unsuppress-map-grouping;
    uses neighbor-weight-grouping;
  }

  grouping ipv4-multicast-neighbor {
    uses neighbor-activate-grouping;
    uses neighbor-additional-paths-grouping;
    uses evpn-neighbor-advertise-grouping;
    uses neighbor-advertise-map-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-aigp-grouping;
    uses neighbor-allow-policy-grouping;
    uses neighbor-allowas-in-grouping;
    uses neighbor-capability-grouping;
    uses neighbor-default-originate-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-flowspec-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping ipv4-flowspec-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping ipv4-sr-policy-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-weight-grouping;
  }

  grouping ipv4-sr-policy-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-weight-grouping;
  }

  grouping ipv4-mvpn-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses peer-group-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-mvpn-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-mdt-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses peer-group-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-mdt-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv6-unicast-neighbor {
    uses neighbor-activate-grouping;
    uses neighbor-additional-paths-grouping;
    uses neighbor-advertise-grouping;
    uses neighbor-advertise-map-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-default-originate-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping {
      refine "route-reflector-client" {
        must 'not(../advertise/best-external)' {
          error-message "route-reflector-client and advertise/best-external cannot be configured at the same time";
        }
      }
    }
    uses neighbor-send-community-grouping;
    uses neighbor-send-label-grouping;
    uses neighbor-slow-peer-grouping;
    uses neighbor-soft-reconfiguration-grouping;
    uses neighbor-soo-grouping;
    uses neighbor-translate-update-grouping;
    uses neighbor-unsuppress-map-grouping;
    uses neighbor-weight-grouping;
  }

  grouping ipv6-multicast-neighbor {
    uses neighbor-activate-grouping;
    uses neighbor-additional-paths-grouping;
    uses evpn-neighbor-advertise-grouping;
    uses neighbor-advertise-map-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-aigp-grouping;
    uses neighbor-allow-policy-grouping;
    uses neighbor-allowas-in-grouping;
    uses neighbor-capability-grouping;
    uses neighbor-default-originate-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv6-flowspec-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping ipv6-flowspec-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping ipv6-mvpn-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses peer-group-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv6-mvpn-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping l2vpn-evpn-peer-group {
    uses neighbor-activate-grouping;
    uses neighbor-additional-paths-grouping;
    uses evpn-neighbor-advertise-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-encap-grouping;
    uses neighbor-filter-list-grouping;
    uses peer-group-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping l2vpn-evpn-neighbor {
    uses neighbor-activate-grouping;
    uses neighbor-additional-paths-grouping;
    uses evpn-neighbor-advertise-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-encap-grouping;
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping l2vpn-vpls-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-length-size-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-suppress-signaling-protocol-grouping;
    leaf unsuppress-map {
      status obsolete;
      description
        "Route-map to selectively unsuppress suppressed routes (OBSOLETE)";
      type string;
    }
    uses neighbor-weight-grouping;
  }

  grouping rtfilter-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses rtfilter-neighbor-default-originate-grouping;
    container default-originate {
      status obsolete;
      description
        "Originate default route to this neighbor (OBSOLETE)";
      presence "enable originate default route to this neighbor";
      leaf route-map {
        status obsolete;
        description
          "Route-map to specify criteria to originate default (OBSOLETE)";
        type string;
      }
    }
    uses neighbor-af-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-weight-grouping;
  }

  grouping vpnv4-unicast-neighbor {
    uses neighbor-activate-grouping;
    uses neighbor-accept-route-legacy-rt-grouping;
    uses neighbor-vpn-advertise-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-inter-as-hybrid-grouping;
    uses neighbor-long-lived-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping {
      refine "route-reflector-client" {
        must 'not(../advertise/best-external)' {
          error-message "route-reflector-client and advertise/best-external cannot be configured at the same time";
        }
      }
    }
    uses neighbor-send-community-grouping;
    uses neighbor-send-label-grouping;
    uses neighbor-slow-peer-grouping;
    uses neighbor-soft-reconfiguration-grouping;
    uses neighbor-soo-grouping;
    uses neighbor-unsuppress-map-grouping;
    uses neighbor-weight-grouping;
  }

  grouping vpnv4-multicast-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping vpnv4-flowspec-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-long-lived-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-validation-grouping;
    uses neighbor-weight-grouping;
  }

  grouping vpnv4-flowspec-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-long-lived-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-validation-grouping;
    uses neighbor-weight-grouping;
  }

  grouping vpnv6-unicast-neighbor {
    uses neighbor-activate-grouping;
    uses neighbor-accept-route-legacy-rt-grouping;
    uses neighbor-vpn-advertise-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-long-lived-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping {
      refine "route-reflector-client" {
        must 'not(../advertise/best-external)' {
          error-message "route-reflector-client and advertise/best-external cannot be configured at the same time";
        }
      }
    }
    uses neighbor-send-community-grouping;
    uses neighbor-slow-peer-grouping;
    uses neighbor-soft-reconfiguration-grouping;
    uses neighbor-soo-grouping;
    uses neighbor-unsuppress-map-grouping;
    uses neighbor-weight-grouping;
  }

  grouping vpnv6-multicast-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-distribute-list-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping vpnv6-flowspec-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-long-lived-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-validation-grouping;
    uses neighbor-weight-grouping;
  }

  grouping vpnv6-flowspec-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-long-lived-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-validation-grouping;
    uses neighbor-weight-grouping;
  }

  grouping nsap-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allow-policy-grouping;
    uses neighbor-allowas-in-grouping;
    uses neighbor-capability-grouping;
    uses neighbor-default-originate-grouping;
    uses neighbor-dmzlink-bw-grouping {
      refine "dmzlink-bw" {
        must 'not(/ios:native/ios:router/ios-bgp:bgp/ios-bgp:peer-group/ios-bgp:neighbor[ios-bgp:id=current()]/ios-bgp:ebgp-multihop)' {
          error-message "Propagation of DMZ-Link-Bandwidth is supported only for single-hop EBGP peers";
        }
      }
    }
    uses neighbor-filter-list-grouping;
    uses neighbor-af-inherit-grouping;
    uses neighbor-maximum-prefix-grouping;
    uses neighbor-next-hop-self-grouping;
    uses neighbor-next-hop-unchanged-v2-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soo-grouping;
    uses neighbor-weight-grouping;
  }

  grouping link-state-peer-group {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses peer-group-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping link-state-neighbor {
    uses neighbor-activate-grouping;
    uses neighbor-advertisement-interval-ebgp-grouping {
      when "(/ios:native/ios:router/ios-bgp:bgp/ios-bgp:id != /ios:native/ios:router/ios-bgp:bgp/ios-bgp:neighbor[ios-bgp:id=current()/ios-bgp:id]/ios-bgp:remote-as)
            or (/ios:native/ios:router/ios-bgp:bgp/ios-bgp:id != /ios:native/ios:router/ios-bgp:bgp/ios-bgp:peer-group/ios-bgp:neighbor[ios-bgp:id=current()/ios-bgp:id]/ios-bgp:remote-as)
            or not(/ios:native/ios:router/ios-bgp:bgp/ios-bgp:peer-group/ios-bgp:neighbor[ios-bgp:id=current()/ios-bgp:id]/ios-bgp:remote-as)";
    }
    uses neighbor-advertisement-interval-grouping;
    uses neighbor-allowas-in-grouping;
    uses neighbor-af-inherit-grouping;
    uses neighbor-maximum-prefix-grouping;
    uses neighbor-next-hop-self-grouping;
    uses neighbor-next-hop-unchanged-v2-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping vrf-ipv4-unicast-neighbor {
    uses neighbor-remote-as-grouping;
    uses neighbor-peer-group-grouping {
      refine "peer-group/peer-group-name" {
        must '(/ios:native/ios:router/ios-bgp:bgp/address-family/with-vrf/ipv4/vrf/ipv4-unicast/peer-group/neighbor[id=current()]/peer-group)' {
          error-message "The peer-group should be configured before attaching with the neighbor";
        }
      }
    }
    uses neighbor-inherit-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-bmp-activate-grouping;
    uses neighbor-capability-grouping;
    uses neighbor-cluster-id-grouping;
    uses neighbor-default-originate-grouping;
    uses neighbor-description-grouping;
    uses neighbor-disable-connected-check-grouping;
    uses neighbor-distribute-list-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remove-private-as-grouping;
    uses neighbor-route-map-grouping;
    uses neighbor-route-reflector-client-grouping;
    uses neighbor-send-community-grouping;
    uses vrf-neighbor-send-label-grouping;
    container send-label {
      status obsolete;
      description
        "Send NLRI + MPLS Label to this peer (OBSOLETE)";
      presence "true";
      leaf send-label-explicit {
        status obsolete;
        type enumeration {
          enum explicit-null;
        }
      }
    }
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv4-multicast-neighbor {
    uses neighbor-remote-as-grouping;
    uses neighbor-peer-group-grouping {
      refine "peer-group/peer-group-name" {
        must '(/ios:native/ios:router/ios-bgp:bgp/address-family/with-vrf/ipv4/vrf/ipv4-multicast/peer-group/neighbor[id=current()]/peer-group)' {
          error-message "The peer-group should be configured before attaching with the neighbor";
        }
      }
    }
    uses neighbor-inherit-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-as-override-grouping;
    uses neighbor-bmp-activate-grouping;
    uses neighbor-capability-grouping;
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv4-flowspec-neighbor {
    uses neighbor-remote-as-grouping;
    uses neighbor-peer-group-grouping {
      refine "peer-group/peer-group-name" {
        must '(/ios:native/ios:router/ios-bgp:bgp/address-family/with-vrf/ipv4/vrf/ipv4-flowspec/peer-group/neighbor[id=current()]/peer-group)' {
          error-message "The peer-group should be configured before attaching with the neighbor";
        }
      }
    }
    uses neighbor-inherit-grouping;
    uses neighbor-activate-grouping;
    uses neighbor-advertisement-interval-grouping {
      refine "advertisement-interval" {
        default "0";
      }
    }
    uses neighbor-allowas-in-grouping;
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-unicast-neighbor {
    uses neighbor-remote-as-grouping;
    uses neighbor-peer-group-grouping {
      refine "peer-group/peer-group-name" {
        must '(/ios:native/ios:router/ios-bgp:bgp/address-family/with-vrf/ipv6/vrf/ipv6-unicast/peer-group/neighbor[id=current()]/peer-group)' {
          error-message "The peer-group should be configured before attaching with the neighbor";
        }
      }
    }
    uses neighbor-inherit-grouping;
    uses neighbor-activate-grouping;
    uses neighbor-advertise-map-grouping;
    uses neighbor-advertisement-interval-grouping {
      refine "advertisement-interval" {
        default "0";
      }
    }
    uses neighbor-aigp-grouping;
    uses neighbor-allow-policy-grouping;
    uses neighbor-allowas-in-grouping;
    uses neighbor-announce-grouping;
    uses neighbor-as-override-grouping;
    uses neighbor-bmp-activate-grouping;
    uses neighbor-capability-grouping;
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remove-private-as-grouping;
    uses neighbor-route-map-grouping;
    uses neighbor-route-reflector-client-grouping;
    uses neighbor-send-community-grouping;
    uses vrf-neighbor-send-label-grouping;
    container send-label {
      status obsolete;
      description
        "Send NLRI + MPLS Label to this peer (OBSOLETE)";
      presence "true";
      leaf send-label-explicit {
        status obsolete;
        type enumeration {
          enum explicit-null;
        }
      }
    }
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-multicast-neighbor {
    uses neighbor-remote-as-grouping;
    uses neighbor-peer-group-grouping {
      refine "peer-group/peer-group-name" {
        must '(/ios:native/ios:router/ios-bgp:bgp/address-family/with-vrf/ipv6/vrf/ipv6-multicast/peer-group/neighbor[id=current()]/peer-group)' {
          error-message "The peer-group should be configured before attaching with the neighbor";
        }
      }
    }
    uses neighbor-inherit-grouping;
    uses neighbor-activate-grouping;
    uses neighbor-advertisement-interval-grouping {
      refine "advertisement-interval" {
        default "0";
      }
    }
    uses neighbor-aigp-grouping;
    uses neighbor-allow-policy-grouping;
    uses neighbor-allowas-in-grouping;
    uses neighbor-as-override-grouping;
    uses neighbor-bmp-activate-grouping;
    uses neighbor-capability-grouping;
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-flowspec-neighbor {
    uses neighbor-remote-as-grouping;
    uses neighbor-peer-group-grouping {
      refine "peer-group/peer-group-name" {
        must '(/ios:native/ios:router/ios-bgp:bgp/address-family/with-vrf/ipv6/vrf/ipv6-flowspec/peer-group/neighbor[id=current()]/peer-group)' {
          error-message "The peer-group should be configured before attaching with the neighbor";
        }
      }
    }
    uses neighbor-inherit-grouping;
    uses neighbor-activate-grouping;
    uses neighbor-advertisement-interval-grouping {
      refine "advertisement-interval" {
        default "0";
      }
    }
    uses neighbor-allowas-in-grouping;
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses neighbor-internal-vpn-client-grouping;
    uses neighbor-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-update-grouping;
    uses neighbor-update-source-grouping;
    uses neighbor-version-grouping;
    uses neighbor-weight-grouping;
  }

  grouping vrf-ipv4-unicast-peergroup {
    uses peer-group-peer-group-grouping;
    uses neighbor-activate-grouping;
    uses neighbor-advertise-map-grouping;
    uses neighbor-advertisement-interval-grouping {
      refine "advertisement-interval" {
        default "0";
      }
    }
    uses neighbor-aigp-grouping;
    uses neighbor-allow-policy-grouping;
    uses neighbor-allowas-in-grouping;
    uses neighbor-announce-grouping;
    uses neighbor-as-override-grouping;
    uses neighbor-bmp-activate-grouping;
    container capability {
      description
        "Advertise capability to the peer";
      container orf {
        description
          "Advertise ORF capability to the peer";
        uses neighbor-capability-peer-group-grouping;
        leaf-list prefix-list {
          status obsolete;
          description
            "Advertise prefix list ORF capability to this neighbor";
          max-elements 1;
          type enumeration {
            enum both;
            enum receive;
            enum send;
          }
        }
      }
    }
    uses neighbor-cluster-id-grouping;
    uses neighbor-default-originate-grouping;
    uses neighbor-description-grouping;
    uses neighbor-disable-connected-check-grouping;
    uses neighbor-distribute-list-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remote-as-grouping;
    uses neighbor-remove-private-as-grouping;
    uses neighbor-route-map-grouping;
    uses neighbor-route-reflector-client-grouping;
    uses neighbor-send-community-grouping;
    uses vrf-neighbor-send-label-grouping;
    container send-label {
      status obsolete;
      description
        "Send NLRI + MPLS Label to this peer (OBSOLETE)";
      presence "true";
      leaf send-label-explicit {
        status obsolete;
        type enumeration {
          enum explicit-null;
        }
      }
    }
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv4-multicast-peergroup {
    uses peer-group-peer-group-grouping;
    uses neighbor-activate-grouping;
    uses neighbor-advertise-map-grouping;
    uses neighbor-advertisement-interval-grouping {
      refine "advertisement-interval" {
        default "0";
      }
    }
    uses neighbor-aigp-grouping;
    uses neighbor-allow-policy-grouping;
    uses neighbor-allowas-in-grouping;
    uses neighbor-as-override-grouping;
    uses neighbor-bmp-activate-grouping;
    container capability {
      description
        "Advertise capability to the peer";
      container orf {
        description
          "Advertise ORF capability to the peer";
        uses neighbor-capability-peer-group-grouping;
        leaf-list prefix-list {
          status obsolete;
          description
            "Advertise prefix list ORF capability to this neighbor";
          max-elements 1;
          type enumeration {
            enum both;
            enum receive;
            enum send;
          }
        }
      }
    }
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv4-flowspec-peergroup {
    uses peer-group-peer-group-grouping;
    uses neighbor-activate-grouping;
    uses neighbor-advertisement-interval-grouping {
      refine "advertisement-interval" {
        default "0";
      }
    }
    uses neighbor-allowas-in-grouping;
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-unicast-peergroup {
    uses peer-group-peer-group-grouping;
    uses neighbor-activate-grouping;
    uses neighbor-advertise-map-grouping;
    uses neighbor-advertisement-interval-grouping {
      refine "advertisement-interval" {
        default "0";
      }
    }
    uses neighbor-aigp-grouping;
    uses neighbor-allow-policy-grouping;
    uses neighbor-allowas-in-grouping;
    uses neighbor-announce-grouping;
    uses neighbor-as-override-grouping;
    uses neighbor-bmp-activate-grouping;
    container capability {
      description
        "Advertise capability to the peer";
      container orf {
        description
          "Advertise ORF capability to the peer";
        uses neighbor-capability-peer-group-grouping;
        leaf-list prefix-list {
          status obsolete;
          description
            "Advertise prefix list ORF capability to this neighbor";
          max-elements 1;
          type enumeration {
            enum both;
            enum receive;
            enum send;
          }
        }
      }
    }
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remote-as-grouping;
    uses neighbor-remove-private-as-grouping;
    uses neighbor-route-map-grouping;
    uses neighbor-route-reflector-client-grouping;
    uses neighbor-send-community-grouping;
    uses vrf-neighbor-send-label-grouping;
    container send-label {
      status obsolete;
      description
        "Send NLRI + MPLS Label to this peer (OBSOLETE)";
      presence "true";
      leaf send-label-explicit {
        status obsolete;
        type enumeration {
          enum explicit-null;
        }
      }
    }
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-multicast-peergroup {
    uses peer-group-peer-group-grouping;
    uses neighbor-activate-grouping;
    uses neighbor-advertisement-interval-grouping {
      refine "advertisement-interval" {
        default "0";
      }
    }
    uses neighbor-aigp-grouping;
    uses neighbor-allow-policy-grouping;
    uses neighbor-allowas-in-grouping;
    uses neighbor-as-override-grouping;
    uses neighbor-bmp-activate-grouping;
    container capability {
      description
        "Advertise capability to the peer";
      container orf {
        description
          "Advertise ORF capability to the peer";
        uses neighbor-capability-peer-group-grouping;
        leaf-list prefix-list {
          status obsolete;
          description
            "Advertise prefix list ORF capability to this neighbor";
          max-elements 1;
          type enumeration {
            enum both;
            enum receive;
            enum send;
          }
        }
      }
    }
    uses neighbor-cluster-id-grouping;
    uses neighbor-default-originate-grouping;
    uses neighbor-description-grouping;
    uses neighbor-disable-connected-check-grouping;
    uses neighbor-dmzlink-bw-grouping {
      refine "dmzlink-bw" {
        must 'not(../ios-bgp:ebgp-multihop)' {
          error-message "Propagation of DMZ-Link-Bandwidth is supported only for single-hop EBGP peers";
        }
      }
    }
    uses neighbor-dont-capability-negotiate-grouping;
    uses neighbor-ebgp-multihop-grouping;
    uses neighbor-fall-over-grouping;
    uses neighbor-filter-list-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-prefix-list-grouping;
    uses neighbor-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-grouping;
    uses neighbor-update-source-grouping;
    uses neighbor-version-grouping;
    uses neighbor-weight-grouping;
  }

  grouping vrf-ipv6-flowspec-peergroup {
    uses peer-group-peer-group-grouping;
    uses neighbor-activate-grouping;
    uses neighbor-advertisement-interval-grouping {
      refine "advertisement-interval" {
        default "0";
      }
    }
    uses neighbor-allowas-in-grouping;
    uses neighbor-bmp-activate-grouping;
    uses neighbor-cluster-id-grouping;
    uses neighbor-description-grouping;
    uses neighbor-disable-connected-check-grouping;
    uses neighbor-dont-capability-negotiate-grouping;
    uses neighbor-ebgp-multihop-grouping;
    uses neighbor-fall-over-grouping;
    uses neighbor-ha-mode-grouping;
    uses peer-group-inherit-grouping;
    uses neighbor-internal-vpn-client-grouping;
    uses neighbor-peer-group-local-as-grouping;
    uses neighbor-log-neighbor-changes-grouping;
    uses neighbor-maximum-prefix-grouping;
    uses neighbor-next-hop-self-grouping;
    uses vrf-neighbor-next-hop-unchanged-v2-grouping;
    uses vrf-neighbor-next-hop-unchanged-grouping;
    uses neighbor-password-grouping;
    uses neighbor-ao-grouping;
    uses neighbor-path-attribute-grouping;
    uses neighbor-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-update-grouping;
    uses neighbor-update-source-grouping;
    uses neighbor-version-grouping;
    uses neighbor-weight-grouping;
  }

  grouping ipv4-unicast-bgp {
    container bgp {
      uses bgp-additional-paths-grouping;
      uses bgp-advertise-best-external-grouping {
        refine "advertise-best-external" {
          must 'not(../additional-paths/select/best-external-backup/best-external)' {
            error-message "advertise-best-external and bgp additional-path select best-external cannot be configured at the same time";
          }
        }
      }
      uses bgp-aggregate-timer-grouping;
      uses bgp-bestpath-grouping;
      uses bgp-dampening-grouping;
      uses bgp-dmzlink-bw-grouping;
      uses bgp-inject-map-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
      uses bgp-sourced-paths-grouping;
      uses bgp-suppress-inactive-grouping;
      uses bgp-update-group-grouping;
    }
  }

  grouping ipv4-multicast-bgp {
    container bgp {
      uses bgp-additional-paths-grouping;
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-sourced-paths-grouping;
      uses bgp-update-group-grouping;
    }
  }

  grouping ipv4-flowspec-bgp {
    container bgp {
      uses bgp-nexthop-grouping;
      uses bgp-route-map-grouping;
      uses bgp-scan-time-grouping;
      uses bgp-slow-peer-grouping;
    }
  }

  grouping ipv4-sr-policy-bgp {
    container bgp {
      uses bgp-nexthop-grouping;
      uses bgp-route-map-grouping;
      uses bgp-scan-time-grouping;
      uses bgp-slow-peer-grouping;
    }
  }

  grouping ipv4-mvpn-bgp {
    container bgp {
      uses bgp-default-grouping;
      uses bgp-dmzlink-bw-grouping;
      uses bgp-nexthop-grouping;
      uses bgp-scan-time-grouping;
      uses bgp-slow-peer-grouping;
      uses bgp-soft-reconfig-backup-grouping;
    }
  }

  grouping ipv4-mdt-bgp {
    container bgp {
      uses bgp-dampening-grouping;
      uses bgp-dmzlink-bw-grouping;
      uses bgp-nexthop-grouping;
      uses bgp-scan-time-grouping;
      uses bgp-slow-peer-grouping;
      uses bgp-soft-reconfig-backup-grouping;
    }
  }

  grouping ipv6-unicast-bgp {
    container bgp {
      uses bgp-additional-paths-grouping;
      uses bgp-advertise-best-external-grouping {
        refine "advertise-best-external" {
          must 'not(../additional-paths/select/best-external-backup/best-external)' {
            error-message "advertise-best-external and bgp additional-path select best-external cannot be configured at the same time";
          }
        }
      }
      uses bgp-aggregate-timer-grouping;
      uses bgp-bestpath-grouping;
      uses bgp-dampening-grouping;
      uses bgp-dmzlink-bw-grouping;
      uses bgp-inject-map-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
      uses bgp-sourced-paths-grouping;
      uses bgp-suppress-inactive-grouping;
      uses bgp-update-group-grouping;
    }
  }

  grouping ipv6-multicast-bgp {
    container bgp {
      uses bgp-additional-paths-grouping;
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-sourced-paths-grouping;
      uses bgp-update-group-grouping;
    }
  }

  grouping ipv6-flowspec-bgp {
    container bgp {
      uses bgp-nexthop-grouping;
      uses bgp-route-map-grouping;
      uses bgp-scan-time-grouping;
      uses bgp-slow-peer-grouping;
    }
  }

  grouping ipv6-mvpn-bgp {
    container bgp {
      uses bgp-default-grouping;
      uses bgp-dmzlink-bw-grouping;
      uses bgp-nexthop-grouping;
      uses bgp-scan-time-grouping;
      uses bgp-slow-peer-grouping;
      uses bgp-soft-reconfig-backup-grouping;
    }
  }

  grouping vpnv4-unicast-bgp {
    container bgp {
      uses bgp-additional-paths-vpn-grouping;
      uses bgp-advertise-best-external-grouping {
        refine "advertise-best-external" {
          must 'not(../additional-paths/select/best-external)' {
            error-message "advertise-best-external and bgp additional-path select best-external cannot be configured at the same time";
          }
        }
      }
      uses bgp-aggregate-timer-grouping;
      uses bgp-bestpath-without-validation-grouping;
      uses bgp-dampening-grouping;
      uses bgp-default-grouping;
      uses bgp-dmzlink-bw-grouping;
      uses bgp-nexthop-grouping;
      uses bgp-recursion-grouping;
      uses bgp-redistribute-internal-grouping;
      uses bgp-route-map-grouping;
      uses bgp-rr-group-grouping;
      uses bgp-scan-time-grouping;
      uses bgp-slow-peer-grouping;
      uses bgp-soft-reconfig-backup-grouping;
      uses bgp-update-group-grouping;
    }
  }

  grouping vpnv4-multicast-bgp {
    container bgp {
      uses bgp-aggregate-timer-grouping;
      uses bgp-dampening-grouping;
      uses bgp-default-grouping;
      uses bgp-dmzlink-bw-grouping;
      uses bgp-nexthop-grouping;
      uses bgp-redistribute-internal-grouping;
      uses bgp-route-map-grouping;
      uses bgp-rr-group-grouping;
      uses bgp-scan-time-grouping;
      uses bgp-slow-peer-grouping;
      uses bgp-soft-reconfig-backup-grouping;
      uses bgp-update-group-grouping;
    }
  }

  grouping vpnv4-flowspec-bgp {
    container bgp {
      uses bgp-nexthop-grouping;
      uses bgp-route-map-grouping;
      uses bgp-scan-time-grouping;
      uses bgp-slow-peer-grouping;
    }
  }

  grouping vpnv6-unicast-bgp {
    container bgp {
      uses bgp-additional-paths-vpn-grouping;
      uses bgp-advertise-best-external-grouping {
        refine "advertise-best-external" {
          must 'not(../additional-paths/select/best-external)' {
            error-message "advertise-best-external and bgp additional-path select best-external cannot be configured at the same time";
          }
        }
      }
      uses bgp-aggregate-timer-grouping;
      uses bgp-bestpath-without-validation-grouping;
      uses bgp-dampening-grouping;
      uses bgp-default-grouping;
      uses bgp-dmzlink-bw-grouping;
      uses bgp-nexthop-grouping;
      uses bgp-recursion-grouping;
      uses bgp-redistribute-internal-grouping;
      uses bgp-route-map-grouping;
      uses bgp-rr-group-grouping;
      uses bgp-scan-time-grouping;
      uses bgp-slow-peer-grouping;
      uses bgp-soft-reconfig-backup-grouping;
      uses bgp-update-group-grouping;
    }
  }

  grouping vpnv6-multicast-bgp {
    container bgp {
      uses bgp-aggregate-timer-grouping;
      uses bgp-dampening-grouping;
      uses bgp-default-grouping;
      uses bgp-dmzlink-bw-grouping;
      uses bgp-nexthop-grouping;
      uses bgp-redistribute-internal-grouping;
      uses bgp-route-map-grouping;
      uses bgp-rr-group-grouping;
      uses bgp-scan-time-grouping;
      uses bgp-slow-peer-grouping;
      uses bgp-soft-reconfig-backup-grouping;
      uses bgp-update-group-grouping;
    }
  }

  grouping vpnv6-flowspec-bgp {
    container bgp {
      uses bgp-nexthop-grouping;
      uses bgp-route-map-grouping;
      uses bgp-scan-time-grouping;
      uses bgp-slow-peer-grouping;
    }
  }

  grouping l2vpn-evpn-bgp {
    container bgp {
      uses bgp-evpn-additional-paths-grouping;
      uses bgp-default-grouping;
      uses bgp-nexthop-grouping;
      uses bgp-scan-time-grouping;
    }
  }

  grouping l2vpn-vpls-bgp {
    container bgp {
      uses bgp-default-grouping;
      uses bgp-nexthop-grouping;
      uses bgp-scan-time-grouping;
      uses bgp-slow-peer-grouping;
    }
  }

  grouping rtfilter-bgp {
    container bgp {
      uses bgp-nexthop-grouping;
      uses bgp-slow-peer-grouping;
    }
  }

  grouping nsap-bgp {
    container bgp {
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
    }
  }

  grouping link-state-bgp {
    container bgp {
      uses bgp-nexthop-grouping;
      uses bgp-route-map-grouping;
      uses bgp-scan-time-grouping;
      uses bgp-slow-peer-grouping;
    }
  }

  grouping vrf-ipv4-unicast-bgp {
    container bgp {
      uses bgp-vrf-additional-paths-grouping;
      uses bgp-advertise-best-external-grouping {
        refine "advertise-best-external" {
          must 'not(../additional-paths/select/best-external-backup/best-external)' {
            error-message "advertise-best-external and bgp additional-path select best-external cannot be configured at the same time";
          }
        }
      }
      uses bgp-aggregate-timer-grouping;
      uses bgp-bestpath-without-validation-grouping;
      uses bgp-dampening-grouping;
      container recursion {
        status obsolete;
        description
          "recursion rule for the nexthops (OBSOLETE)";
        leaf host {
          status obsolete;
          description
            "recursion via host for the nexthops (OBSOLETE)";
          type empty;
        }
      }
      uses bgp-redistribute-internal-obsolete-grouping;
      uses bgp-route-map-grouping;
      uses bgp-vrf-router-id-grouping;
      uses bgp-slow-peer-grouping;
      uses bgp-sourced-paths-grouping;
      uses bgp-suppress-inactive-grouping;
      uses bgp-listen-vrf-grouping;
    }
  }

  grouping vrf-ipv4-multicast-bgp {
    container bgp {
      uses bgp-vrf-additional-paths-grouping;
      uses bgp-aggregate-timer-grouping;
      uses bgp-dampening-grouping;
      uses bgp-redistribute-internal-obsolete-grouping;
      uses bgp-sourced-paths-grouping;
      uses bgp-route-map-grouping;
      uses bgp-slow-peer-grouping;
    }
  }

  grouping vrf-ipv6-unicast-bgp {
    container bgp {
      uses bgp-vrf-additional-paths-grouping;
      uses bgp-advertise-best-external-grouping {
        refine "advertise-best-external" {
          must 'not(../additional-paths/select/best-external-backup/best-external)' {
            error-message "advertise-best-external and bgp additional-path select best-external cannot be configured at the same time";
          }
        }
      }
      uses bgp-aggregate-timer-grouping;
      uses bgp-bestpath-without-validation-grouping;
      uses bgp-dampening-grouping;
      container recursion {
        status obsolete;
        description
          "recursion rule for the nexthops (OBSOLETE)";
        leaf host {
          status obsolete;
          description
            "recursion via host for the nexthops (OBSOLETE)";
          type empty;
        }
      }
      uses bgp-redistribute-internal-obsolete-grouping;
      uses bgp-route-map-grouping;
      uses bgp-vrf-router-id-grouping;
      uses bgp-slow-peer-grouping;
      uses bgp-sourced-paths-grouping;
      uses bgp-suppress-inactive-grouping;
      uses bgp-listen-vrf-grouping;
    }
  }

  grouping vrf-ipv6-multicast-bgp {
    container bgp {
      uses bgp-vrf-additional-paths-grouping;
      uses bgp-aggregate-timer-grouping;
      uses bgp-dampening-grouping;
      uses bgp-redistribute-internal-obsolete-grouping;
      uses bgp-sourced-paths-grouping;
      uses bgp-route-map-grouping;
      uses bgp-slow-peer-grouping;
    }
  }

  grouping ipv4-unicast-grouping {
    container ipv4-unicast {
      description
        "IPv4 Unicast address family";
      when "(../ios-bgp:af-name = 'unicast')";
      uses address-family-ipv4-aggregate-address-grouping;
      uses address-family-auto-summary-grouping;
      uses ipv4-unicast-bgp;
      uses address-family-default-information-grouping;
      uses address-family-default-metric-grouping;
      uses address-family-distance-grouping;
      uses address-family-distribute-list-grouping;
      uses address-family-ipv4-maximum-paths-grouping;
      container peer-group {
        list neighbor {
          description
            "Specify a neighbor router";
          must 'count(*) > 1';
          key "id";
          leaf id {
            type string;
          }
          uses neighbor-activate-grouping;
          uses neighbor-additional-paths-grouping;
          uses neighbor-advertise-grouping;
          uses neighbor-advertise-map-grouping;
          uses neighbor-advertisement-interval-grouping;
          uses neighbor-aigp-grouping;
          uses neighbor-allow-policy-grouping;
          uses neighbor-allowas-in-grouping;
          uses neighbor-announce-grouping;
          uses neighbor-as-override-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-default-originate-grouping;
          uses neighbor-distribute-list-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping {
            refine "route-reflector-client" {
              must 'not(../advertise/best-external)' {
                error-message "route-reflector-client and advertise/best-external cannot be configured at the same time";
              }
            }
          }
          uses neighbor-send-community-grouping;
          uses neighbor-send-label-grouping;
          uses neighbor-slow-peer-grouping;
          uses neighbor-soft-reconfiguration-grouping;
          uses neighbor-soo-grouping;
          uses neighbor-translate-update-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses ipv4-unicast-neighbor {
          refine "activate" {
            mandatory true;
          }
        }
      }
      uses address-family-ipv4-network-grouping;
      uses address-family-redistribute-grouping;
      uses address-family-segment-routing-grouping;
      uses address-family-snmp-grouping;
      uses address-family-synchronization-grouping;
      uses address-family-table-map-grouping;
    }
  }

  grouping ipv4-multicast-grouping {
    container ipv4-multicast {
      description
        "IPv4 Multicast address family";
      when "(../ios-bgp:af-name = 'multicast')";
      uses address-family-ipv4-aggregate-address-grouping;
      uses address-family-auto-summary-grouping;
      uses ipv4-multicast-bgp;
      uses address-family-default-information-grouping;
      uses address-family-default-metric-grouping;
      uses address-family-distance-grouping;
      container peer-group {
        list neighbor {
          description
            "Specify a neighbor router";
          must 'count(*) > 1';
          key "id";
          leaf id {
            type string;
          }
          uses neighbor-activate-grouping;
          uses neighbor-additional-paths-grouping;
          uses evpn-neighbor-advertise-grouping;
          uses neighbor-advertise-map-grouping;
          uses neighbor-advertisement-interval-grouping;
          uses neighbor-aigp-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-default-originate-grouping;
          uses neighbor-distribute-list-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping;
          uses neighbor-send-community-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses ipv4-multicast-neighbor {
          refine "activate" {
            mandatory true;
          }
        }
      }
      uses address-family-ipv4-network-grouping;
      uses address-family-redistribute-grouping;
      uses address-family-snmp-grouping;
      uses address-family-table-map-grouping;
    }
  }

  grouping ipv4-flowspec-grouping {
    container ipv4-flowspec {
      description
        "Ipv4 Flowspec address family";
      when "(../ios-bgp:af-name = 'flowspec')";
      uses ipv4-flowspec-bgp;
      uses address-family-default-information-grouping;
      uses address-family-default-metric-grouping;
      uses address-family-ipv4-maximum-paths-grouping;
      container peer-group {
        list neighbor {
          description
            "Specify a neighbor router";
          must 'count(*) > 1';
          key "id";
          leaf id {
            type string;
          }
          uses ipv4-flowspec-peer-group;
        }
      }
      list neighbor {
        description
          "Specify a neighbor router";
        must 'count(*) > 1';
        key "id";
        leaf id {
          type union {
            type inet:ip-address;
            type ios-types:ipv6-link-local-interface-address;
          }
        }
        uses ipv4-flowspec-neighbor {
          refine "activate" {
            mandatory true;
          }
        }
      }
      uses address-family-ipv4-network-grouping;
      uses address-family-redistribute-grouping-obsolete;
      uses address-family-snmp-grouping;
    }
  }

  grouping ipv4-sr-policy-grouping {
    container ipv4-sr-policy {
      if-feature "ios-features:sr-policy";
      description
        "IPv4 SR-Policy address family";
      when "(../ios-bgp:af-name = 'sr-policy')";
      uses ipv4-sr-policy-bgp;
      container peer-group {
        list neighbor {
          description
            "Specify a neighbor router";
          must 'count(*) > 1';
          key "id";
          leaf id {
            type string;
          }
          uses ipv4-sr-policy-peer-group;
        }
      }
      list neighbor {
        description
          "Specify a neighbor router";
        must 'count(*) > 1';
        key "id";
        leaf id {
          type union {
            type inet:ip-address;
            type ios-types:ipv6-link-local-interface-address;
          }
        }
        uses ipv4-sr-policy-neighbor {
          refine "activate" {
            mandatory true;
          }
        }
      }
      uses address-family-snmp-grouping;
    }
  }

  grouping ipv4-mvpn-grouping {
    container ipv4-mvpn {
      description
        "IPv4 MVPN address family";
      when "(../ios-bgp:af-name = 'mvpn')";
      uses ipv4-mvpn-bgp;
      uses address-family-default-information-grouping;
      container peer-group {
        list neighbor {
          description
            "Specify a neighbor router";
          must 'count(*) > 1';
          key "id";
          leaf id {
            type string;
          }
          uses ipv4-mvpn-peer-group;
        }
      }
      list neighbor {
        description
          "Specify a neighbor router";
        must 'count(*) > 1';
        key "id";
        leaf id {
          type union {
            type inet:ip-address;
            type ios-types:ipv6-link-local-interface-address;
          }
        }
        uses ipv4-mvpn-neighbor {
          refine "activate" {
            mandatory true;
          }
        }
      }
      uses address-family-snmp-grouping;
    }
  }

  grouping ipv4-mdt-grouping {
    container ipv4-mdt {
      description
        "IPv4 MDT address family";
      when "(../ios-bgp:af-name = 'mdt')";
      uses ipv4-mdt-bgp;
      uses address-family-default-information-grouping;
      container peer-group {
        list neighbor {
          description
            "Specify a neighbor router";
          must 'count(*) > 1';
          key "id";
          leaf id {
            type string;
          }
          uses ipv4-mdt-peer-group;
        }
      }
      list neighbor {
        description
          "Specify a neighbor router";
        must 'count(*) > 1';
        key "id";
        leaf id {
          type union {
            type inet:ip-address;
            type ios-types:ipv6-link-local-interface-address;
          }
        }
        uses ipv4-mdt-neighbor {
          refine "activate" {
            mandatory true;
          }
        }
      }
      uses address-family-snmp-grouping;
    }
  }

  grouping ipv6-unicast-grouping {
    container ipv6-unicast {
      description
        "IPv6 Unicast address family";
      when "(../ios-bgp:af-name = 'unicast')";
      uses address-family-ipv6-aggregate-address-grouping;
      uses ipv6-unicast-bgp;
      uses address-family-default-information-grouping;
      uses address-family-default-metric-grouping;
      uses address-family-ipv6-distance-grouping;
      uses address-family-ipv4-maximum-paths-grouping;
      uses address-family-ipv6-label-mode-grouping;
      container peer-group {
        list neighbor {
          description
            "Specify a neighbor router";
          must 'count(*) > 1';
          key "id";
          leaf id {
            type string;
          }
          uses neighbor-activate-grouping;
          uses neighbor-additional-paths-grouping;
          uses neighbor-advertise-grouping;
          uses neighbor-advertise-map-grouping;
          uses neighbor-advertisement-interval-grouping;
          uses neighbor-aigp-grouping;
          uses neighbor-allow-policy-grouping;
          uses neighbor-allowas-in-grouping;
          uses neighbor-announce-grouping;
          uses neighbor-as-override-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-default-originate-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping {
            refine "route-reflector-client" {
              must 'not(../advertise/best-external)' {
                error-message "route-reflector-client and advertise/best-external cannot be configured at the same time";
              }
            }
          }
          uses neighbor-send-community-grouping;
          uses neighbor-send-label-grouping;
          uses neighbor-slow-peer-grouping;
          uses neighbor-soft-reconfiguration-grouping;
          uses neighbor-soo-grouping;
          uses neighbor-translate-update-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses ipv6-unicast-neighbor {
          refine "activate" {
            mandatory true;
          }
        }
      }
      uses address-family-ipv6-network-grouping;
      uses address-family-v6-redistribute-grouping;
      uses address-family-redistribute-grouping-obsolete;
      uses address-family-snmp-grouping;
      uses address-family-synchronization-grouping;
      uses address-family-table-map-grouping;
    }
  }

  grouping ipv6-multicast-grouping {
    container ipv6-multicast {
      description
        "IPv6 Multicast address family";
      when "(../ios-bgp:af-name = 'multicast')";
      uses address-family-ipv6-aggregate-address-grouping;
      uses ipv6-multicast-bgp;
      container distance {
        status obsolete;
        description
          "Define an administrative distance (OBSOLETE)";
        container bgp {
          status obsolete;
          description
            "BGP distance (OBSOLETE)";
          leaf extern-as {
            status obsolete;
            type uint16 {
              range "1..255";
            }
          }
          leaf internal-as {
            status obsolete;
            type uint16 {
              range "1..255";
            }
          }
          leaf local {
            status obsolete;
            type uint16 {
              range "1..255";
            }
          }
        }
        list adm-distance {
          status obsolete;
          description
            "(OBSOLETE)";
          key "distance srcip wildbits";
          leaf distance {
            status obsolete;
            type uint16 {
              range "1..255";
            }
          }
          leaf srcip {
            status obsolete;
            type inet:ipv4-address;
          }
          leaf wildbits {
            status obsolete;
            type inet:ipv4-address;
          }
          leaf acl {
            status obsolete;
            type union {
              type uint16 {
                range "1..99";
              }
              type uint16 {
                range "1300..1999";
              }
              type string {
                pattern '[a-zA-Z].*';
              }
            }
          }
        }
      }
      container peer-group {
        list neighbor {
          description
            "Specify a neighbor router";
          must 'count(*) > 1';
          key "id";
          leaf id {
            type string;
          }
          uses neighbor-activate-grouping;
          uses neighbor-additional-paths-grouping;
          uses evpn-neighbor-advertise-grouping;
          uses neighbor-advertise-map-grouping;
          uses neighbor-advertisement-interval-grouping;
          uses neighbor-aigp-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-default-originate-grouping;
          uses neighbor-distribute-list-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping;
          uses neighbor-send-community-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses ipv6-multicast-neighbor {
          refine "activate" {
            mandatory true;
          }
        }
      }
      uses address-family-ipv6-network-grouping;
      uses address-family-v6-redistribute-grouping;
      uses address-family-redistribute-grouping-obsolete;
      uses address-family-snmp-grouping;
    }
  }

  grouping ipv6-flowspec-grouping {
    container ipv6-flowspec {
      description
        "IPv6 Flowspec address family";
      when "(../ios-bgp:af-name = 'flowspec')";
      uses address-family-ipv6-aggregate-address-grouping;
      uses ipv6-flowspec-bgp;
      uses address-family-default-information-grouping;
      uses address-family-default-metric-grouping;
      container distance {
        status obsolete;
        description
          "Define an administrative distance (OBSOLETE)";
        container bgp {
          status obsolete;
          description
            "BGP distance (OBSOLETE)";
          leaf extern-as {
            status obsolete;
            type uint16 {
              range "1..255";
            }
          }
          leaf internal-as {
            status obsolete;
            type uint16 {
              range "1..255";
            }
          }
          leaf local {
            status obsolete;
            type uint16 {
              range "1..255";
            }
          }
        }
        list adm-distance {
          status obsolete;
          description
            "(OBSOLETE)";
          key "distance srcip wildbits";
          leaf distance {
            status obsolete;
            type uint16 {
              range "1..255";
            }
          }
          leaf srcip {
            status obsolete;
            type inet:ipv4-address;
          }
          leaf wildbits {
            status obsolete;
            type inet:ipv4-address;
          }
          leaf acl {
            status obsolete;
            type union {
              type uint16 {
                range "1..99";
              }
              type uint16 {
                range "1300..1999";
              }
              type string {
                pattern '[a-zA-Z].*';
              }
            }
          }
        }
      }
      container peer-group {
        list neighbor {
          description
            "Specify a neighbor router";
          must 'count(*) > 1';
          key "id";
          leaf id {
            type string;
          }
          uses ipv6-flowspec-peer-group;
        }
      }
      list neighbor {
        description
          "Specify a neighbor router";
        must 'count(*) > 1';
        key "id";
        leaf id {
          type union {
            type inet:ip-address;
            type ios-types:ipv6-link-local-interface-address;
          }
        }
        uses ipv6-flowspec-neighbor {
          refine "activate" {
            mandatory true;
          }
        }
      }
      uses address-family-ipv6-network-grouping;
      uses address-family-redistribute-grouping-obsolete;
      uses address-family-snmp-grouping;
    }
  }

  grouping ipv6-mvpn-grouping {
    container ipv6-mvpn {
      description
        "IPv6 MVPN address family";
      when "(../ios-bgp:af-name = 'mvpn')";
      uses ipv6-mvpn-bgp;
      uses address-family-default-information-grouping;
      container peer-group {
        list neighbor {
          description
            "Specify a neighbor router";
          must 'count(*) > 1';
          key "id";
          leaf id {
            type string;
          }
          uses ipv6-mvpn-peer-group;
        }
      }
      list neighbor {
        description
          "Specify a neighbor router";
        must 'count(*) > 1';
        key "id";
        leaf id {
          type union {
            type inet:ip-address;
            type ios-types:ipv6-link-local-interface-address;
          }
        }
        uses ipv6-mvpn-neighbor {
          refine "activate" {
            mandatory true;
          }
        }
      }
      uses address-family-snmp-grouping;
    }
  }

  grouping vpnv4-unicast-grouping {
    container vpnv4-unicast {
      description
        "VPNv4 Unicast address family";
      when "(../ios-bgp:af-name = 'unicast')";
      uses vpnv4-unicast-bgp;
      uses address-family-vpnv4-import-grouping;
      uses address-family-vpnv4-maximum-paths-grouping;
      container peer-group {
        list neighbor {
          description
            "Specify a neighbor router";
          must 'count(*) > 1';
          key "id";
          leaf id {
            type string;
          }
          uses neighbor-accept-route-legacy-rt-grouping;
          uses neighbor-activate-grouping;
          uses neighbor-vpn-advertise-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-distribute-list-grouping;
          uses neighbor-dmzlink-bw-grouping;
          uses neighbor-filter-list-grouping;
          uses peer-group-inherit-grouping;
          uses neighbor-inter-as-hybrid-grouping;
          uses neighbor-long-lived-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping {
            refine "route-reflector-client" {
              must 'not(../advertise/best-external)' {
                error-message "route-reflector-client and advertise/best-external cannot be configured at the same time";
              }
            }
          }
          uses neighbor-send-community-grouping;
          uses neighbor-send-label-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses vpnv4-unicast-neighbor {
          refine "activate" {
            mandatory true;
          }
        }
      }
      uses address-family-ipv4-network-grouping;
      uses address-family-snmp-grouping;
    }
  }

  grouping vpnv4-multicast-grouping {
    container vpnv4-multicast {
      description
        "VPNv4 Multicast address family";
      when "(../ios-bgp:af-name = 'multicast')";
      uses vpnv4-multicast-bgp;
      uses address-family-vpnv4-maximum-paths-grouping;
      container peer-group {
        list neighbor {
          description
            "Specify a neighbor router";
          must 'count(*) > 1';
          key "id";
          leaf id {
            type string;
          }
          uses neighbor-activate-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-distribute-list-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping;
          uses neighbor-send-community-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses vpnv4-multicast-neighbor {
          refine "activate" {
            mandatory true;
          }
        }
      }
      uses address-family-snmp-grouping;
    }
  }

  grouping vpnv4-flowspec-grouping {
    container vpnv4-flowspec {
      description
        "VPNv4 Flowspec address family";
      when "(../ios-bgp:af-name = 'flowspec')";
      uses vpnv4-flowspec-bgp;
      uses address-family-maximum-paths-ebgp-grouping;
      container peer-group {
        list neighbor {
          description
            "Specify a neighbor router";
          must 'count(*) > 1';
          key "id";
          leaf id {
            type string;
          }
          uses vpnv4-flowspec-peer-group;
        }
      }
      list neighbor {
        description
          "Specify a neighbor router";
        must 'count(*) > 1';
        key "id";
        leaf id {
          type union {
            type inet:ip-address;
            type ios-types:ipv6-link-local-interface-address;
          }
        }
        uses vpnv4-flowspec-neighbor {
          refine "activate" {
            mandatory true;
          }
        }
      }
      uses address-family-snmp-grouping;
    }
  }

  grouping vpnv6-unicast-grouping {
    container vpnv6-unicast {
      description
        "VPNv6 Unicast address family";
      when "(../ios-bgp:af-name = 'unicast')";
      uses vpnv6-unicast-bgp;
      uses address-family-vpnv6-import-grouping;
      container peer-group {
        list neighbor {
          description
            "Specify a neighbor router";
          must 'count(*) > 1';
          key "id";
          leaf id {
            type string;
          }
          uses neighbor-accept-route-legacy-rt-grouping;
          uses neighbor-activate-grouping;
          uses neighbor-vpn-advertise-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-distribute-list-grouping;
          uses neighbor-dmzlink-bw-grouping;
          uses neighbor-filter-list-grouping;
          uses peer-group-inherit-grouping;
          uses neighbor-long-lived-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping {
            refine "route-reflector-client" {
              must 'not(../advertise/best-external)' {
                error-message "route-reflector-client and advertise/best-external cannot be configured at the same time";
              }
            }
          }
          uses neighbor-send-community-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses vpnv6-unicast-neighbor {
          refine "activate" {
            mandatory true;
          }
        }
      }
      uses address-family-snmp-grouping;
    }
  }

  grouping vpnv6-multicast-grouping {
    container vpnv6-multicast {
      description
        "VPNv6 Multicast address family";
      when "(../ios-bgp:af-name = 'multicast')";
      uses vpnv6-multicast-bgp;
      container peer-group {
        list neighbor {
          description
            "Specify a neighbor router";
          must 'count(*) > 1';
          key "id";
          leaf id {
            type string;
          }
          uses neighbor-activate-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-distribute-list-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping;
          uses neighbor-send-community-grouping;
          uses neighbor-slow-peer-grouping;
          uses neighbor-soft-reconfiguration-grouping;
          uses neighbor-soo-grouping;
          uses neighbor-unsuppress-map-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses vpnv6-multicast-neighbor {
          refine "activate" {
            mandatory true;
          }
        }
      }
      uses address-family-snmp-grouping;
    }
  }

  grouping vpnv6-flowspec-grouping {
    container vpnv6-flowspec {
      description
        "VPNv6 Flowspec address family";
      when "(../ios-bgp:af-name = 'flowspec')";
      uses vpnv6-flowspec-bgp;
      uses address-family-maximum-paths-ebgp-grouping;
      container peer-group {
        list neighbor {
          description
            "Specify a neighbor router";
          must 'count(*) > 1';
          key "id";
          leaf id {
            type string;
          }
          uses vpnv6-flowspec-peer-group;
        }
      }
      list neighbor {
        description
          "Specify a neighbor router";
        must 'count(*) > 1';
        key "id";
        leaf id {
          type union {
            type inet:ip-address;
            type ios-types:ipv6-link-local-interface-address;
          }
        }
        uses vpnv6-flowspec-neighbor {
          refine "activate" {
            mandatory true;
          }
        }
      }
      uses address-family-snmp-grouping;
    }
  }

  grouping l2vpn-vpls-grouping {
    container l2vpn-vpls {
      if-feature "ios-features:l2vpn";
      description
        "L2VPN VPLS address family";
      when "(../ios-bgp:af-name = 'vpls')";
      uses l2vpn-vpls-bgp;
      uses address-family-default-information-grouping;
      container peer-group {
        list neighbor {
          description
            "Specify a neighbor router";
          must 'count(*) > 1';
          key "id";
          leaf id {
            type string;
          }
          uses neighbor-activate-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses peer-group-inherit-grouping;
          uses neighbor-maximum-prefix-grouping;
          uses neighbor-next-hop-self-grouping;
          uses neighbor-next-hop-unchanged-v2-grouping;
          uses neighbor-next-hop-unchanged-grouping;
          uses neighbor-prefix-length-size-grouping;
          uses neighbor-remove-private-as-grouping;
          uses neighbor-route-map-grouping;
          uses neighbor-route-reflector-client-grouping;
          uses neighbor-send-community-grouping;
          uses neighbor-slow-peer-grouping;
          uses neighbor-soft-reconfiguration-grouping;
          uses neighbor-soo-grouping;
          uses neighbor-suppress-signaling-protocol-grouping;
          uses neighbor-unsuppress-map-grouping {
            status obsolete;
          }
          uses neighbor-weight-grouping;
        }
      }
      list neighbor {
        description
          "Specify a neighbor router";
        must 'count(*) > 1';
        key "id";
        leaf id {
          type union {
            type inet:ip-address;
            type ios-types:ipv6-link-local-interface-address;
          }
        }
        uses l2vpn-vpls-neighbor {
          refine "activate" {
            mandatory true;
          }
        }
      }
      uses address-family-snmp-grouping;
    }
  }

  grouping l2vpn-evpn-grouping {
    container l2vpn-evpn {
      if-feature "ios-features:l2vpn";
      description
        "L2VPN EVPN address family";
      when "(../ios-bgp:af-name = 'evpn')";
      uses l2vpn-evpn-bgp;
      container default-information {
        status obsolete;
        description
          "Control distribution of default information (OBSOLETE)";
        leaf originate {
          status obsolete;
          description
            "Distribute a default route (OBSOLETE)";
          type empty;
        }
      }
      leaf default-metric {
        status obsolete;
        description
          "Set metric of redistributed routes (OBSOLETE)";
        type uint32 {
          range "1..4294967295";
        }
      }
      uses address-family-l2vpn-import-grouping;
      container maximum-paths {
        status obsolete;
        description
          "Forward packets over multiple paths (OBSOLETE)";
        leaf ebgp {
          status obsolete;
          description
            "eBGP-multipath (OBSOLETE)";
          type uint16 {
            range "1..32";
          }
        }
        leaf eibgp {
          status obsolete;
          description
            "Both eBGP and iBGP paths as multipath (OBSOLETE)";
          type uint16 {
            range "1..32";
          }
        }
        container ibgp {
          status obsolete;
          description
            "iBGP-multipath (OBSOLETE)";
          choice ibgp-choice {
            status obsolete;
            leaf unequal-cost {
              status obsolete;
              description
                "Perform un-equal cost multipath selection (OBSOLETE)";
              type uint16 {
                range "1..32";
              }
            }
            leaf max {
              status obsolete;
              type uint16 {
                range "1..32";
              }
            }
          }
        }
      }
      uses evpn-rewrite-rt-grouping;
      container peer-group {
        list neighbor {
          description
            "Specify a neighbor router";
          must 'count(*) > 1';
          key "id";
          leaf id {
            type string;
          }
          uses l2vpn-evpn-peer-group;
        }
      }
      list neighbor {
        description
          "Specify a neighbor router";
        must 'count(*) > 1';
        key "id";
        leaf id {
          type union {
            type inet:ip-address;
            type ios-types:ipv6-link-local-interface-address;
          }
        }
        uses l2vpn-evpn-neighbor {
          refine "activate" {
            mandatory true;
          }
        }
      }
      leaf activate {
        description
          "Enable the address family for this neighbor";
        status obsolete;
        type empty;
      }
      leaf advertisement-interval {
        description
          "Minimum interval between sending BGP routing updates";
        status obsolete;
        type uint16 {
          range "0..600";
        }
      }
      container allowas-in {
        description
          "Accept as-path with my AS present in it";
        presence "accept as-paths";
        status obsolete;
        leaf as-number {
          status obsolete;
          type uint8 {
            range "1..10";
          }
        }
      }
      leaf allow-policy {
        status obsolete;
        description
          "Enable the policy support for this IBGP Neighbor";
        type empty;
      }
      container capability {
        status obsolete;
        description
          "Advertise capability to the peer";
        container orf {
          status obsolete;
          description
            "Advertise ORF capability to the peer";
          leaf-list prefix-list {
            status obsolete;
            description
              "Advertise prefix list ORF capability to this neighbor";
            max-elements 1;
            type enumeration {
              enum both;
              enum receive;
              enum send;
            }
          }
        }
      }
      uses peer-group-inherit-grouping;
      container maximum-prefix {
        description
          "Maximum number of prefixes accepted from this peer";
        status obsolete;
        leaf max-prefix-no {
          status obsolete;
          description
            "maximum no. of prefix limit";
          type uint32 {
            range "1..2147483647";
          }
        }
        leaf threshold {
          when '(../max-prefix-no)';
          status obsolete;
          default "75";
          type uint8 {
            range "1..100";
          }
        }
        leaf restart {
          status obsolete;
          description
            "Restart bgp connection after limit is exceeded";
          type uint16 {
            range "1..65535";
          }
          must 'not(../warning-only)' {
            error-message
              "restart and warning-only cannot be configured at the
               same time";
          }
        }
        leaf warning-only {
          status obsolete;
          description
            "Only give warning message when limit is exceeded";
          type empty;
        }
      }
      container next-hop-self {
        status obsolete;
        description
          "Disable the next hop calculation for this neighbor";
        presence "true";
        leaf all {
          status obsolete;
          description
            "Enable next-hop-self for both eBGP and iBGP received paths";
          type empty;
        }
      }
      leaf next-hop-unchanged {
        status obsolete;
        description
          "Propagate the iBGP paths' next hop unchanged for this neighbor";
        type empty;
      }
      container remove-private-as {
        description
          "Remove private AS number from outbound updates";
        status obsolete;
        presence "true";
        container all {
          description
            "Remove all private AS numbers";
          status obsolete;
          presence "true";
          leaf replace-as {
            status obsolete;
            description
              "Replace all private AS numbers with local AS";
            type empty;
          }
        }
      }
      list route-map {
        status obsolete;
        description
          "Apply route map to neighbor";
        key "inout";
        leaf inout {
          status obsolete;
          type enumeration {
            enum in;
            enum out;
          }
        }
        leaf route-map-name {
          status obsolete;
          type string;
          mandatory true;
        }
      }
      leaf route-reflector-client {
        status obsolete;
        description
          "Configure a neighbor as Route Reflector client";
        type empty;
      }
      container send-community {
        description
          "Send Community attribute to this neighbor";
        status obsolete;
        presence "true";
        leaf send-community-where {
          status obsolete;
          default "standard";
          type enumeration {
            enum both;
            enum extended;
            enum standard;
          }
        }
      }
      container slow-peer {
        status obsolete;
        description
          "Configure slow-peer";
        container detection {
          status obsolete;
          description
            "Slow-peer detection";
          presence "true";
          leaf threshold {
            status obsolete;
            description
              "Threshold value (seconds)";
            type uint16 {
              range "120..3600";
            }
          }
          leaf disable {
            status obsolete;
            description
              "Disable slow-peer detection";
            type empty;
          }
          must '(not(threshold) and disable) or (threshold and not(disable))' {
            error-message "thresold and disable can't be configured at the same time";
          }
        }
        container split-update-group {
          status obsolete;
          description
            "Configure slow-peer split-update-group";
          container dynamic {
            status obsolete;
            description
              "Dynamically split the slow peer to slow-update group";
            presence "true";
            leaf permanent {
              status obsolete;
              description
                "Keep the slow-peer permanently in slow-update group";
              type empty;
            }
            leaf disable {
              status obsolete;
              description
                "Disable slow-peer detection";
              type empty;
            }
            must '(not(permanent) and disable) or (permanent and not(disable))' {
              error-message "permanent and disable can't be configured at the same time";
            }
          }
          leaf static {
            status obsolete;
            description
              "Static slow-peer";
            type empty;
          }
        }
      }
      leaf soft-reconfiguration {
        status obsolete;
        description
          "Per neighbor soft reconfiguration";
        type enumeration {
          enum inbound;
        }
      }
      leaf soo {
        status obsolete;
        description
          "ASN:nn or IP-address:nn VPN extended community";
        type string {
          pattern '[0-9]*:[0-9]*|[0-9.]*:[0-9]*';
        }
      }
      leaf unsuppress-map {
        description
          "Route-map to selectively unsuppress suppressed routes";
        status obsolete;
        type string;
      }
      leaf weight {
        status obsolete;
        description
          "Set default weight for routes from this neighbor";
        type uint16 {
          range "0..65535";
        }
      }
      uses address-family-ipv4-network-grouping;
      uses address-family-snmp-grouping;
    }
  }

  grouping nsap-grouping {
    container nsap {
      description
        "NSAP address family";
      when "(../ios-bgp:af-name = 'unicast')";
      uses nsap-bgp;
      uses address-family-default-information-grouping;
      uses address-family-default-metric-grouping;
      uses address-family-maximum-paths-ebgp-grouping;
      container peer-group {
        list neighbor {
          description
            "Specify a neighbor router";
          must 'count(*) > 1';
          key "id";
          leaf id {
            type string;
          }
          uses neighbor-activate-grouping;
          uses neighbor-advertisement-interval-grouping;
          uses neighbor-allow-policy-grouping;
          uses neighbor-allowas-in-grouping;
          container capability {
            description
              "Advertise capability to the peer";
            container orf {
              description
                "Advertise ORF capability to the peer";
              uses neighbor-capability-peer-group-grouping;
              leaf-list prefix-list {
                status obsolete;
                description
                  "Advertise prefix list ORF capability to this neighbor";
                max-elements 1;
                type enumeration {
                  enum both;
                  enum receive;
                  enum send;
                }
              }
            }
          }
          uses neighbor-default-originate-grouping;
          uses neighbor-dmzlink-bw-grouping;
          uses neighbor-filter-list-grouping;
          uses peer-group-inherit-grouping;
          uses neighbor-maximum-prefix-grouping;
          uses neighbor-next-hop-self-grouping;
          uses neighbor-next-hop-unchanged-v2-grouping;
          uses neighbor-next-hop-unchanged-grouping;
          uses neighbor-prefix-list-grouping;
          uses neighbor-remove-private-as-grouping;
          uses neighbor-route-map-grouping;
          uses neighbor-route-reflector-client-grouping;
          uses neighbor-send-community-grouping;
          uses neighbor-slow-peer-grouping;
          uses neighbor-soo-grouping;
          uses neighbor-weight-grouping;
        }
      }
      list neighbor {
        description
          "Specify a neighbor router";
        must 'count(*) > 1';
        key "id";
        leaf id {
          type union {
            type inet:ip-address;
            type ios-types:ipv6-link-local-interface-address;
          }
        }
        uses nsap-neighbor {
          refine "activate" {
            mandatory true;
          }
        }
      }
      uses address-family-nsap-network-grouping;
      uses address-family-snmp-grouping;
    }
  }

  grouping rtfilter-grouping {
    container rtfilter {
      description
        "RT-Filter address family";
      when "(../ios-bgp:af-name = 'unicast')";
      uses rtfilter-bgp;
      uses address-family-rtf-maximum-paths-grouping;
      list neighbor {
        description
          "Specify a neighbor router";
        must 'count(*) > 1';
        key "id";
        leaf id {
          type inet:ip-address;
        }
        uses rtfilter-neighbor {
          refine "activate" {
            mandatory true;
          }
        }
      }
      uses address-family-snmp-grouping;
    }
  }

  grouping link-state-grouping {
    container link-state {
      description
        "link-state family";
      when "(../ios-bgp:af-name = 'link-state')";
      uses link-state-bgp;
      uses address-family-maximum-paths-ebgp-grouping;
      uses address-family-link-state-domain-distinguisher-grouping;
      container peer-group {
        list neighbor {
          description
            "Specify a neighbor router";
          must 'count(*) > 1';
          key "id";
          leaf id {
            type string;
          }
          uses link-state-peer-group;
        }
      }
      list neighbor {
        description
          "Specify a neighbor router";
        must 'count(*) > 1';
        key "id";
        leaf id {
          type union {
            type inet:ip-address;
            type ios-types:ipv6-link-local-interface-address;
          }
        }
        uses link-state-neighbor {
          refine "activate" {
            mandatory true;
          }
        }
      }
      uses address-family-link-state-propagate-aspath-grouping;
      uses address-family-snmp-grouping;
    }
  }

  grouping vrf-ipv4-unicast-grouping {
    container ipv4-unicast {
      description
        "IPv4 Unicast VRF address family";
      when "(../../ios-bgp:af-name = 'unicast')";
      uses address-family-advertise-grouping;
      uses address-family-ipv4-aggregate-address-grouping;
      uses vrf-ipv4-unicast-bgp;
      uses address-family-default-information-grouping;
      uses address-family-default-metric-grouping;
      uses address-family-distance-grouping;
      uses address-family-distribute-list-grouping;
      uses address-family-vrf-import-grouping;
      uses address-family-maximum-paths-grouping;
      uses address-family-mvpn-select-grouping;
      container peer-group {
        list neighbor {
          description
            "Specify a neighbor router";
          must 'count(*) > 1';
          key "id";
          leaf id {
            type string;
          }
          uses vrf-ipv4-unicast-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv4-unicast-neighbor {
          refine "activate" {
            mandatory true;
          }
          refine "remote-as";
        }
      }
      uses address-family-vrf-ipv4-network-grouping;
      uses address-family-propagate-aspath-grouping;
      uses address-family-vrf-redistribute-grouping;
      uses address-family-redistribute-grouping-obsolete;
      uses address-family-snmp-grouping;
      uses address-family-synchronization-grouping;
      uses address-family-table-map-grouping;
    }
  }

  grouping vrf-ipv4-multicast-grouping {
    container ipv4-multicast {
      description
        "IPv4 Multicast VRF address family";
      when "(../../ios-bgp:af-name = 'multicast')";
      uses address-family-ipv4-aggregate-address-grouping;
      uses vrf-ipv4-multicast-bgp;
      uses address-family-default-information-grouping;
      uses address-family-default-metric-grouping;
      uses address-family-distance-grouping;
      uses address-family-vrf-import-grouping;
      container peer-group {
        list neighbor {
          description
            "Specify a neighbor router";
          must 'count(*) > 1';
          key "id";
          leaf id {
            type string;
          }
          uses vrf-ipv4-multicast-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv4-multicast-neighbor {
          refine "activate" {
            mandatory true;
          }
        }
      }
      uses address-family-vrf-ipv4-network-grouping;
      uses address-family-propagate-aspath-grouping;
      uses address-family-vrf-redistribute-grouping;
      uses address-family-redistribute-grouping-obsolete;
      uses address-family-snmp-grouping;
      uses address-family-table-map-grouping;
    }
  }

  grouping vrf-ipv4-flowspec-grouping {
    container ipv4-flowspec {
      description
        "IPv4 Flowspec VRF address family";
      when "(../../ios-bgp:af-name = 'flowspec')";
      container bgp {
        uses bgp-route-map-grouping;
        uses bgp-slow-peer-grouping;
      }
      uses address-family-default-information-grouping;
      uses address-family-default-metric-grouping;
      uses address-family-vrf-import-grouping;
      uses address-family-maximum-paths-ebgp-grouping;
      container peer-group {
        list neighbor {
          description
            "Specify a neighbor router";
          must 'count(*) > 1';
          key "id";
          leaf id {
            type string;
          }
          uses vrf-ipv4-flowspec-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv4-flowspec-neighbor {
          refine "activate" {
            mandatory true;
          }
        }
      }
      uses address-family-vrf-ipv4-network-grouping;
      uses address-family-propagate-aspath-grouping;
      uses address-family-snmp-grouping;
    }
  }

  grouping vrf-ipv4-mvpn-grouping {
    container ipv4-mvpn {
      description
        "IPv4 MVPN VRF address family";
      when "(../../ios-bgp:af-name = 'mvpn')";
      container bgp {
        uses bgp-dampening-grouping;
      }
    }
  }

  grouping vrf-ipv6-unicast-grouping {
    container ipv6-unicast {
      description
        "IPv6 Unicast VRF address family";
      when "(../../ios-bgp:af-name = 'unicast')";
      uses address-family-advertise-grouping;
      uses address-family-ipv6-aggregate-address-grouping;
      uses vrf-ipv6-unicast-bgp;
      uses address-family-default-information-grouping;
      uses address-family-default-metric-grouping;
      uses address-family-ipv6-distance-grouping;
      uses address-family-vrf-import-grouping;
      uses address-family-maximum-paths-grouping;
      container peer-group {
        list neighbor {
          description
            "Specify a neighbor router";
          must 'count(*) > 1';
          key "id";
          leaf id {
            type string;
          }
          uses vrf-ipv6-unicast-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv6-unicast-neighbor {
          refine "activate" {
            mandatory true;
          }
        }
      }
      uses address-family-vrf-ipv6-network-grouping;
      uses address-family-propagate-aspath-grouping;
      uses address-family-v6-redistribute-grouping;
      uses address-family-redistribute-grouping-obsolete;
      uses address-family-snmp-grouping;
      uses address-family-synchronization-grouping;
      uses address-family-table-map-grouping;
    }
  }

  grouping vrf-ipv6-multicast-grouping {
    container ipv6-multicast {
      description
        "IPv6 Multicast VRF address family";
      when "(../../ios-bgp:af-name = 'multicast')";
      uses address-family-ipv6-aggregate-address-grouping;
      uses vrf-ipv6-multicast-bgp;
      container distance {
        status obsolete;
        description
          "Define an administrative distance (OBSOLETE)";
        container bgp {
          status obsolete;
          description
            "BGP distance (OBSOLETE)";
          leaf extern-as {
            status obsolete;
            type uint16 {
              range "1..255";
            }
          }
          leaf internal-as {
            status obsolete;
            type uint16 {
              range "1..255";
            }
          }
          leaf local {
            status obsolete;
            type uint16 {
              range "1..255";
            }
          }
        }
        list adm-distance {
          status obsolete;
          description
            "(OBSOLETE)";
          key "distance srcip wildbits";
          leaf distance {
            status obsolete;
            type uint16 {
              range "1..255";
            }
          }
          leaf srcip {
            status obsolete;
            type inet:ipv4-address;
          }
          leaf wildbits {
            status obsolete;
            type inet:ipv4-address;
          }
          leaf acl {
            status obsolete;
            type union {
              type uint16 {
                range "1..99";
              }
              type uint16 {
                range "1300..1999";
              }
              type string {
                pattern '[a-zA-Z].*';
              }
            }
          }
        }
      }
      uses address-family-vrf-import-grouping;
      container peer-group {
        list neighbor {
          description
            "Specify a neighbor router";
          must 'count(*) > 1';
          key "id";
          leaf id {
            type string;
          }
          uses vrf-ipv6-multicast-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv6-multicast-neighbor {
          refine "activate" {
            mandatory true;
          }
        }
      }
      uses address-family-vrf-ipv6-network-grouping;
      uses address-family-propagate-aspath-grouping;
      uses address-family-v6-redistribute-grouping;
      uses address-family-redistribute-grouping-obsolete;
      uses address-family-snmp-grouping;
    }
  }

  grouping vrf-ipv6-flowspec-grouping {
    container ipv6-flowspec {
      description
        "IPv6 Flowspec VRF address family";
      when "(../../ios-bgp:af-name = 'flowspec')";
      uses address-family-ipv6-aggregate-address-grouping;
      container bgp {
        uses bgp-route-map-grouping;
        uses bgp-slow-peer-grouping;
      }
      uses address-family-default-information-grouping;
      uses address-family-default-metric-grouping;
      container distance {
        status obsolete;
        description
          "Define an administrative distance (OBSOLETE)";
        container bgp {
          status obsolete;
          description
            "BGP distance (OBSOLETE)";
          leaf extern-as {
            status obsolete;
            type uint16 {
              range "1..255";
            }
          }
          leaf internal-as {
            status obsolete;
            type uint16 {
              range "1..255";
            }
          }
          leaf local {
            status obsolete;
            type uint16 {
              range "1..255";
            }
          }
        }
        list adm-distance {
          status obsolete;
          description
            "(OBSOLETE)";
          key "distance srcip wildbits";
          leaf distance {
            status obsolete;
            type uint16 {
              range "1..255";
            }
          }
          leaf srcip {
            status obsolete;
            type inet:ipv4-address;
          }
          leaf wildbits {
            status obsolete;
            type inet:ipv4-address;
          }
          leaf acl {
            status obsolete;
            type union {
              type uint16 {
                range "1..99";
              }
              type uint16 {
                range "1300..1999";
              }
              type string {
                pattern '[a-zA-Z].*';
              }
            }
          }
        }
      }
      uses address-family-vrf-import-grouping;
      container maximum-paths {
        status obsolete;
        description
          "Forward packets over multiple paths (OBSOLETE)";
        leaf ebgp {
          status obsolete;
          description
            "eBGP-multipath (OBSOLETE)";
          type uint16 {
            range "1..32";
          }
        }
        leaf eibgp {
          status obsolete;
          description
            "Both eBGP and iBGP paths as multipath (OBSOLETE)";
          type uint16 {
            range "1..32";
          }
        }
        container ibgp {
          status obsolete;
          description
            "iBGP-multipath (OBSOLETE)";
          choice ibgp-choice {
            status obsolete;
            leaf unequal-cost {
              status obsolete;
              description
                "Perform un-equal cost multipath selection (OBSOLETE)";
              type uint16 {
                range "1..32";
              }
            }
            leaf max {
              status obsolete;
              type uint16 {
                range "1..32";
              }
            }
          }
        }
      }
      container peer-group {
        list neighbor {
          description
            "Specify a neighbor router";
          must 'count(*) > 1';
          key "id";
          leaf id {
            type string;
          }
          uses vrf-ipv6-flowspec-peergroup;
        }
      }
      list neighbor {
        description
          "Specify a neighbor router";
        must 'count(*) > 1';
        key "id";
        leaf id {
          type union {
            type inet:ip-address;
            type ios-types:ipv6-link-local-interface-address;
          }
          must "((../../ios-bgp:neighbor[ios-bgp:id=current()]/remote-as) or
                (../../ios-bgp:neighbor[ios-bgp:id=current()]/ios-bgp:peer-group/ios-bgp:peer-group-name) or
                (../../ios-bgp:neighbor[ios-bgp:id=current()]/ios-bgp:inherit/ios-bgp:peer-session))" {
            error-message "Neighbor must be activated and neighbor must have remote-as or peer-group or peer-session template configured";
          }
        }
        uses vrf-ipv6-flowspec-neighbor {
          refine "activate" {
            mandatory true;
          }
        }
      }
      uses address-family-vrf-ipv6-network-grouping;
      uses address-family-propagate-aspath-grouping;
      uses address-family-v6-redistribute-grouping-obsolete;
      uses address-family-redistribute-grouping-obsolete;
      uses address-family-snmp-grouping;
    }
  }

  grouping vrf-ipv6-mvpn-grouping {
    container ipv6-mvpn {
      description
        "IPv6 MVPN VRF address family";
      when "(../../ios-bgp:af-name = 'mvpn')";
      container bgp {
        uses bgp-dampening-grouping;
      }
      uses address-family-snmp-grouping;
    }
  }

  grouping address-family-no-vrf-grouping {
    container no-vrf {
      list ipv4 {
        description
          "Address family";
        key "af-name";
        leaf af-name {
          type ios-types:bgp_ipv4_af_type;
        }
        uses ipv4-unicast-grouping;
      }
      list ipv6 {
        description
          "Address family";
        key "af-name";
        leaf af-name {
          type ios-types:bgp_ipv6_af_type;
        }
        uses ipv6-unicast-grouping;
      }
      list vpnv4 {
        description
          "Address family";
        key "af-name";
        leaf af-name {
          type enumeration {
            enum unicast;
            enum multicast;
            enum flowspec;
          }
        }
        uses vpnv4-unicast-grouping;
      }
      list vpnv6 {
        description
          "Address family";
        key "af-name";
        leaf af-name {
          type enumeration {
            enum unicast;
            enum multicast;
            enum flowspec;
          }
        }
        uses vpnv6-unicast-grouping;
      }
      list nsap {
        description
          "Address family";
        key "af-name";
        leaf af-name {
          type enumeration {
            enum unicast;
          }
        }
        uses nsap-grouping;
      }
      list l2vpn {
        if-feature "ios-features:l2vpn";
        description
          "Address family";
        key "af-name";
        leaf af-name {
          type enumeration {
            enum evpn;
            enum vpls;
          }
        }
        uses l2vpn-evpn-grouping;
        uses l2vpn-vpls-grouping;
      }
      list rtfilter {
        description
          "Address family";
        key "af-name";
        leaf af-name {
          type enumeration {
            enum unicast;
          }
        }
        uses rtfilter-grouping;
      }
      list link-state {
        description
          "Address family";
        key "af-name";
        leaf af-name {
          type enumeration {
            enum link-state;
          }
        }
        uses link-state-grouping;
      }
    }
  }

  grouping ip-community-list-standard-grouping {
    container deny {
      description
        "Specify community to reject";
      leaf-list deny-list {
        ordered-by user;
        type union {
          type ios-types:community-number-type;
          type ios-types:community-well-known-type;
        }
      }
    }
    container permit {
      description
        "Specify community to accept";
      leaf-list permit-list {
        ordered-by user;
        type union {
          type ios-types:community-number-type;
          type ios-types:community-well-known-type;
        }
      }
    }
  }

  grouping ip-community-list-expanded-grouping {
    container extended-grouping {
      description
        "Community list entry";
      list extended_grouping {
        description
          "Specify community list to accept or deny";
        ordered-by user;
        key "action string";
        leaf action {
          type enumeration {
            enum deny;
            enum permit;
          }
        }
        leaf string {
          type string {
            pattern '.*';
          }
        }
      }
    }
  }

  grouping ip-large-community-list-standard-grouping {
    container deny {
      description
        "Specify large-community to reject";
      leaf-list deny-list {
        description
          "large-community deny list";
        ordered-by user;
        type union {
          type ios-types:large-community-number-type;
        }
      }
    }
    container permit {
      description
        "Specify large-community to accept";
      leaf-list permit-list {
        description
          "large-community permit list";
        ordered-by user;
        type union {
          type ios-types:large-community-number-type;
        }
      }
    }
  }

  grouping ip-large-community-list-expanded-grouping {
    container extended-grouping {
      description
        "Large community list entry";
      list extended_grouping {
        description
          "Specify large-community list to accept or deny";
        ordered-by user;
        key "action string";
        leaf action {
          description
            "Specify community to accept or reject";
          type enumeration {
            enum deny;
            enum permit;
          }
        }
        leaf string {
          description
            "Specify community";
          type string {
            pattern '.*';
          }
        }
      }
    }
  }

  grouping ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }

  grouping config-ip-community-list-grouping {
    container community-list {
      description
        "Add a community list entry";
      list number-standard {
        key "no";
        leaf no {
          type uint16 {
            range "1..99";
          }
        }
        must 'deny/deny-list or permit/permit-list' {
          error-message
            "community-list must be configured with
             permit or deny";
        }
        uses ip-community-list-standard-grouping;
      }
      list number-expanded {
        key "no";
        leaf no {
          type uint16 {
            range "100..500";
          }
        }
        must 'extended-grouping/extended_grouping' {
          error-message
            "community-list must be configured with
             permit or deny";
        }
        uses ip-community-list-expanded-grouping;
      }
      list expanded {
        description
          "Add an expanded community-list entry";
        key "name";
        leaf name {
          type string;
        }
        must 'extended-grouping/extended_grouping' {
          error-message
            "community-list must be configured with
             permit or deny";
        }
        uses ip-community-list-expanded-grouping;
      }
      list standard {
        description
          "Add a standard community-list entry";
        key "name";
        leaf name {
          type string;
        }
        must 'deny/deny-list or permit/permit-list' {
          error-message
            "community-list must be configured with
             permit or deny";
        }
        uses ip-community-list-standard-grouping;
      }
    }
  }

  grouping config-ip-large-community-list-grouping {
    container large-community-list {
      description
        "Add a large-community list entry";
      list number-standard {
        description
          "Community list number (standard)";
        key "no";
        leaf no {
          description
            "Community list number";
          type uint16 {
            range "1..99";
          }
        }
        must 'deny/deny-list or permit/permit-list' {
          error-message
            "large-community-list must be configured with
             permit or deny";
        }
        uses ip-large-community-list-standard-grouping;
      }
      list number-expanded {
        description
          "Community list number (expanded)";
        key "no";
        leaf no {
          description
            "Community list number";
          type uint16 {
            range "100..500";
          }
        }
        must 'extended-grouping/extended_grouping' {
          error-message
            "community-list must be configured with
             permit or deny";
        }
        uses ip-large-community-list-expanded-grouping;
      }
      list expanded {
        description
          "Add an expanded large-community-list entry";
        key "name";
        leaf name {
          description
            "Expanded large-community-list name";
          type string;
        }
        must 'extended-grouping/extended_grouping' {
          error-message
            "large-community-list must be configured with
             permit or deny";
        }
        uses ip-large-community-list-expanded-grouping;
      }
      list standard {
        description
          "Add a standard large-community-list entry";
        key "name";
        leaf name {
          description
            "Standard large-community-list name";
          type string;
        }
        must 'deny/deny-list or permit/permit-list' {
          error-message
            "large-community-list must be configured with
             permit or deny";
        }
        uses ip-large-community-list-standard-grouping;
      }
    }
  }

  grouping config-ip-extcommunity-list-grouping {
    container extcommunity-list {
      description
        "Extended a community list entry";
      list number-standard {
        key "no";
        leaf no {
          type uint16 {
            range "1..99";
          }
        }
        must "(deny/rt or deny/soo or deny/vpn-distinguisher) or
              (permit/rt or permit/soo or permit/vpn-distinguisher)" {
          error-message "extcommunity-list must be configured with permit or deny";
        }
        uses ip-extcommunity-list-standard-grouping;
      }
      list number-expanded {
        key "no";
        leaf no {
          type uint16 {
            range "100..500";
          }
        }
        must 'extended-grouping/extended_grouping' {
          error-message
            "community-list must be configured with
             permit or deny";
        }
        uses ip-community-list-expanded-grouping;
      }
      list expanded {
        description
          "Extended an expanded community-list entry";
        key "name";
        leaf name {
          type string;
        }
        must 'extended-grouping/extended_grouping' {
          error-message
            "community-list must be configured with
             permit or deny";
        }
        uses ip-community-list-expanded-grouping;
      }
      list standard {
        description
          "Extended a standard community-list entry";
        key "name";
        leaf name {
          type string;
        }
        must "(deny/rt or deny/soo or deny/vpn-distinguisher) or
              (permit/rt or permit/soo or permit/vpn-distinguisher)" {
          error-message "extcommunity-list must be configured with permit or deny";
        }
        uses ip-extcommunity-list-standard-grouping;
      }
    }
  }

  grouping config-ip-as-path-grouping {
    list access-list {
      description
        "Specify an access list number";
      key "name";
      leaf name {
        type uint16 {
          range "1..500";
        }
      }
      must 'extended-grouping/extended_grouping' {
        error-message
          "community-list must be configured with
           permit or deny";
      }
      uses ip-community-list-expanded-grouping;
    }
  }

  grouping config-bgp-grouping {
    list bgp {
      description
        "Border Gateway Protocol (BGP)";
      must '/ios:native/ios:ip/ios:routing-conf/ios:routing' {
        error-message "To delete ip routing, bgp needs to be deleted 1st";
      }
      key "id";
      max-elements 1;
      leaf id {
        type ios-types:bgp-as-number-type;
      }
      container bgp {
        uses global-bgp-grouping;
      }
      container template {
        description
          "Enter template command mode";
        list peer-policy {
          description
            "Template configuration for policy parameters";
          key "name";
          leaf name {
            type string;
          }
          uses neighbor-accept-route-legacy-rt-grouping;
          uses neighbor-additional-paths-grouping;
          uses neighbor-advertise-grouping;
          uses neighbor-advertise-map-grouping;
          uses neighbor-advertisement-interval-grouping;
          uses neighbor-aigp-grouping;
          uses neighbor-allow-policy-grouping;
          uses neighbor-allowas-in-grouping;
          uses neighbor-announce-grouping;
          uses neighbor-as-override-grouping;
          uses neighbor-capability-grouping;
          uses neighbor-default-originate-grouping;
          uses neighbor-distribute-list-grouping;
          uses neighbor-dmzlink-bw-grouping;
          container encap {
            description
              "Preferred Encapsulation for Neighbor";
            choice encap-choice {
              leaf mpls {
                description
                  "Neighbor Prefers MPLS";
                type empty;
              }
              leaf vxlan {
                description
                  "Neighbor Prefers VxLAN";
                type empty;
              }
            }
          }
          uses template-filter-list-grouping;
          list filter-list {
            status obsolete;
            description
              "Establish BGP filters (OBSOLETE)";
            key "filter-range";
            leaf filter-range {
              status obsolete;
              description
                "AS path access lis (OBSOLETE)";
              type uint16 {
                range "1..500";
              }
            }
            leaf in {
              status obsolete;
              description
                "Filter incoming routes (OBSOLETE)";
              type empty;
            }
            leaf out {
              status obsolete;
              description
                "Filter out-going routes (OBSOLETE)";
              type empty;
            }
          }
          container inherit {
            description
              "Inherit a template";
            container peer-policy {
              list template {
                key "name";
                leaf name {
                  description
                    "Template name";
                  type string;
                }
                leaf range {
                  description
                    "Sequence number";
                  type uint16 {
                    range "1..65535";
                  }
                  mandatory true;
                }
              }
            }
          }
          uses neighbor-inter-as-hybrid-grouping;
          uses neighbor-internal-vpn-client-grouping;
          uses neighbor-long-lived-grouping;
          uses neighbor-maximum-prefix-grouping;
          uses neighbor-next-hop-self-grouping;
          uses neighbor-next-hop-unchanged-v2-grouping;
          uses neighbor-next-hop-unchanged-grouping;
          uses neighbor-prefix-length-size-grouping;
          uses neighbor-prefix-list-grouping;
          uses neighbor-remove-private-as-grouping;
          uses template-route-map-grouping;
          list route-map {
            status obsolete;
            description
              "Apply route map to neighbor (OBSOLETE)";
            key "name";
            leaf name {
              status obsolete;
              description
                "(OBSOLETE)";
              type string;
            }
            leaf in {
              status obsolete;
              description
                "Apply map to incoming routes (OBSOLETE)";
              type empty;
            }
            leaf out {
              status obsolete;
              description
                "Apply map to outgoing routes (OBSOLETE)";
              type empty;
            }
          }
          uses neighbor-route-reflector-client-grouping;
          uses neighbor-send-community-grouping;
          uses neighbor-send-label-grouping;
          uses neighbor-slow-peer-grouping;
          uses neighbor-soft-reconfiguration-grouping;
          uses neighbor-soo-grouping;
          uses neighbor-suppress-signaling-protocol-grouping;
          leaf suppress-sr {
            description
              "Suppress Segment Routing for Neighbor";
            type empty;
          }
          container translate-topology {
            leaf range {
              description
                "Topology id";
              type uint16 {
                range "1..4095";
              }
            }
          }
          uses neighbor-unsuppress-map-grouping;
          uses neighbor-weight-grouping;
          uses neighbor-validation-grouping;
        }
        list peer-session {
          description
            "Template configuration for session parameters";
          key "name";
          leaf name {
            type string;
          }
          uses neighbor-cluster-id-grouping;
          uses neighbor-description-grouping;
          uses neighbor-disable-connected-check-grouping;
          uses neighbor-ebgp-multihop-grouping;
          uses neighbor-fall-over-grouping;
          container ha-mode {
            description
              "high availability mode";
            container graceful-restart {
              description
                "graceful-restart for this peer";
              presence "true";
              leaf disable {
                description
                  "disable graceful-restart";
                type empty;
              }
            }
            container sso {
              description
                "stateful-switchover support for this peer";
              presence "true";
              leaf disable {
                description
                  "disable stateful-switchover";
                type empty;
              }
            }
          }
          uses template-peer-session-inherit-grouping;
          uses template-local-as-grouping;
          uses neighbor-log-neighbor-changes-grouping;
          uses neighbor-password-grouping;
          uses neighbor-path-attribute-grouping;
          uses neighbor-peer-group-obsolete-grouping;
          leaf remote-as {
            description
              "Specify a BGP neighbor remote-as";
            type ios-types:bgp-as-number-type;
          }
          uses neighbor-shutdown-grouping;
          uses neighbor-timers-grouping;
          uses neighbor-transport-grouping;
          uses neighbor-ttl-security-grouping;
          uses neighbor-update-grouping;
          container update-source {
            description
              "Source of routing updates";
            container interface {
              uses ios:interface-with-dependency-grouping;
            }
            uses ios-ifc:interface-deprecated-grouping;
          }
          leaf version {
            description
              "Set the BGP version to match a neighbor";
            default "4";
            type uint8 {
              range "4";
            }
          }
        }
      }
      container peer-group {
        list neighbor {
          description
            "Specify a neighbor router";
          must 'count(*) > 1';
          key "id";
          leaf id {
            type string;
          }
          uses global-peer-group;
        }
      }
      list neighbor {
        description
          "Specify a neighbor router";
        must 'count(*) > 1';
        key "id";
        leaf id {
          type union {
            type inet:ip-address;
            type ios-types:ipv6-link-local-interface-address;
          }
          must "(/ios:native/ios:router/ios-bgp:bgp/ios-bgp:neighbor[ios-bgp:id=current()]/remote-as) or
                (/ios:native/ios:router/ios-bgp:bgp/ios-bgp:neighbor[ios-bgp:id=current()]/ios-bgp:peer-group/ios-bgp:peer-group-name) or
                (/ios:native/ios:router/ios-bgp:bgp/ios-bgp:neighbor[ios-bgp:id=current()]/ios-bgp:inherit/ios-bgp:peer-session)" {
            error-message "Neighbor must have remote-as or peer-group or peer-session template configured";
          }
        }
        uses global-neighbor;
      }
      container address-family {
        description
          "Enter Address Family command mode";
        container with-vrf {
          list ipv4 {
            description
              "Address family";
            key "af-name";
            leaf af-name {
              type ios-types:bgp_ipv4_af_type;
            }
            list vrf {
              key "name";
              leaf name {
                type string;
                must '/ios:native/ios:vrf/ios:definition[ios:name=current()]/ios:rd or /ios:native/ios:ip/ios:vrf[ios:name=current()]/ios:rd' {
                  error-message "To delete vrf/rd, bgp/address-family/vrf needs to be deleted 1st";
                }
              }
              uses vrf-ipv4-unicast-grouping;
              uses vrf-ipv4-multicast-grouping;
              uses vrf-ipv4-flowspec-grouping;
              uses vrf-ipv4-mvpn-grouping;
            }
          }
          list ipv6 {
            description
              "Address family";
            key "af-name";
            leaf af-name {
              type ios-types:bgp_ipv6_af_type;
            }
            list vrf {
              key "name";
              leaf name {
                must '/ios:native/ios:vrf/ios:definition[ios:name=current()]' {
                  error-message "VRF must be created 1st, deleted last";
                }
                type string;
              }
              uses vrf-ipv6-unicast-grouping;
              uses vrf-ipv6-multicast-grouping;
              uses vrf-ipv6-flowspec-grouping;
              uses vrf-ipv6-mvpn-grouping;
            }
          }
        }
        container no-vrf {
          list ipv4 {
            description
              "Address family";
            key "af-name";
            leaf af-name {
              type ios-types:bgp_ipv4_af_type;
            }
            uses ipv4-unicast-grouping;
            uses ipv4-multicast-grouping;
            uses ipv4-flowspec-grouping;
            uses ipv4-sr-policy-grouping;
            uses ipv4-mvpn-grouping;
            uses ipv4-mdt-grouping;
          }
          list ipv6 {
            description
              "Address family";
            key "af-name";
            leaf af-name {
              type ios-types:bgp_ipv6_af_type;
            }
            uses ipv6-unicast-grouping;
            uses ipv6-multicast-grouping;
            uses ipv6-flowspec-grouping;
            uses ipv6-mvpn-grouping;
          }
          list vpnv4 {
            description
              "Address family";
            key "af-name";
            leaf af-name {
              type enumeration {
                enum unicast;
                enum multicast;
                enum flowspec;
              }
            }
            uses vpnv4-unicast-grouping;
            uses vpnv4-multicast-grouping;
            uses vpnv4-flowspec-grouping;
          }
          list vpnv6 {
            description
              "Address family";
            key "af-name";
            leaf af-name {
              type enumeration {
                enum unicast;
                enum multicast;
                enum flowspec;
              }
            }
            uses vpnv6-unicast-grouping;
            uses vpnv6-multicast-grouping;
            uses vpnv6-flowspec-grouping;
          }
          list nsap {
            description
              "Address family";
            key "af-name";
            leaf af-name {
              type enumeration {
                enum unicast;
              }
            }
            uses nsap-grouping;
          }
          list l2vpn {
            if-feature "ios-features:l2vpn";
            description
              "Address family";
            key "af-name";
            leaf af-name {
              type enumeration {
                enum evpn;
                enum vpls;
              }
            }
            uses l2vpn-evpn-grouping;
            uses l2vpn-vpls-grouping;
          }
          list rtfilter {
            description
              "Address family";
            key "af-name";
            leaf af-name {
              type enumeration {
                enum unicast;
              }
            }
            uses rtfilter-grouping;
          }
          list link-state {
            description
              "Address family";
            key "af-name";
            leaf af-name {
              type enumeration {
                enum link-state;
              }
            }
            uses link-state-grouping;
          }
        }
      }
      container timers {
        description
          "Adjust routing timers";
        container bgp {
          description
            "BGP timers";
          leaf keepalive-interval {
            default "60";
            type uint16 {
              range "0..65535";
            }
          }
          leaf holdtime {
            default "180";
            type uint16 {
              range "0..65535";
            }
          }
          leaf minimum-neighbor-hold {
            type uint16 {
              range "0..65535";
            }
          }
          must '((keepalive-interval and holdtime) or ( not(keepalive-interval) and not(holdtime) and not(minimum-neighbor-hold))) and (((keepalive-interval < holdtime) and holdtime != 0) or ((keepalive-interval = 0) and (holdtime = 0)))' {
            error-message
              "Keepalive-interval and holdtime must be configured.
               Holdtime should be greater than the keepalive time.
               If holdtime is 0, keepalive time should also be 0";
          }
        }
      }
      container scope {
        container global {
          presence "true";
          container peer-group {
            list neighbor {
              description
                "Specify a neighbor router";
              must 'count(*) > 1';
              key "id";
              leaf id {
                type string;
              }
              uses peer-group-peer-group-grouping;
              uses neighbor-remote-as-grouping;
              uses neighbor-description-grouping;
              uses neighbor-password-grouping;
              uses neighbor-ao-grouping;
              uses neighbor-update-source-grouping;
              uses neighbor-version-grouping;
            }
          }
          list neighbor {
            description
              "Specify a neighbor router";
            must 'count(*) > 1';
            key "id";
            leaf id {
              type union {
                type inet:ip-address;
                type ios-types:ipv6-link-local-interface-address;
              }
            }
            uses neighbor-remote-as-grouping;
            uses neighbor-peer-group-grouping;
            uses neighbor-description-grouping;
            uses neighbor-password-grouping;
            uses neighbor-ao-grouping;
            uses neighbor-update-source-grouping;
            uses neighbor-version-grouping;
          }
          container address-family {
            description
              "Enter Address Family command mode";
            uses address-family-no-vrf-grouping;
          }
        }
        list vrf {
          key "id";
          leaf id {
            type union {
              type inet:ipv4-address;
              type inet:ipv6-address;
              type string;
            }
          }
          container peer-group {
            list neighbor {
              description
                "Specify a neighbor router";
              must 'count(*) > 1';
              key "id";
              leaf id {
                type string;
              }
              uses peer-group-peer-group-grouping;
              uses neighbor-remote-as-grouping;
            }
          }
          list neighbor {
            description
              "Specify a neighbor router";
            must 'count(*) > 1';
            key "id";
            leaf id {
              type union {
                type inet:ip-address;
                type ios-types:ipv6-link-local-interface-address;
              }
            }
            uses neighbor-peer-group-grouping;
            uses neighbor-remote-as-grouping;
          }
          container address-family {
            description
              "Enter Address Family command mode";
            uses address-family-no-vrf-grouping;
          }
        }
      }
    }
  }

  augment "/ios:native/ios:router" {
    uses config-bgp-grouping;
  }

  augment "/ios:native/ios:ip" {
    uses config-ip-community-list-grouping;
  }

  augment "/ios:native/ios:ip" {
    uses config-ip-extcommunity-list-grouping;
  }

  augment "/ios:native/ios:ip" {
    uses config-ip-large-community-list-grouping;
  }

  augment "/ios:native/ios:ip/ios:as-path" {
    uses config-ip-as-path-grouping;
  }
}
