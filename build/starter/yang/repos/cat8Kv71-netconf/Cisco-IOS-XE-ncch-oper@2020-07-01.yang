module Cisco-IOS-XE-ncch-oper {
  yang-version 1;
  namespace "http://cisco.com/ns/yang/Cisco-IOS-XE-ncch-oper";
  prefix ncch-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for operational data of NETCONF server Call Home.
     Copyright (c) 2020 by Cisco Systems, Inc.
     All rights reserved.";

  revision 2020-07-01 {
    description
      "Initial revision";
    reference
      "1.0.0";
    cisco-semver:module-version "1.0.0";
  }

  typedef ncch-client-state {
    type enumeration {
      enum client-state-connecting {
        value 0;
        description
          "Attempts are being made to connect to
           the NETCONF client.";
      }
      enum client-state-connected {
        value 1;
        description
          "A call-home connection has been established.";
      }
    }
    description
      "States of a NETCONF client.";
  }

  grouping ncch-client-oper {
    description
      "Operational data of a NETCONF client.";
    leaf name {
      type string;
      description
        "Name of the remote NETCONF client.";
    }
    leaf state {
      type ncch-oper:ncch-client-state;
      description
        "State of the NETCONF client.";
    }
    leaf connected-endpoint {
      when "(../state = 'client-state-connected')";
      type string;
      description
        "A call-home connection has been established between
         one of the endpoints of this NETCONF client and
         the NETCONF server. Specifies the name of the connected endpoint.";
    }
    leaf connect-time {
      when "(../state = 'client-state-connected')";
      type yang:date-and-time;
      description
        "A call-home connection has been established between
         one of the endpoints of this NETCONF client and
         the NETCONF server. Specifies the timestamp when the endpoint
         got connected.";
    }
  }

  container netconf-callhome-oper {
    config false;
    description
      "Operational data of NETCONF server Call Home.";
    list ncch-client {
      key "name";
      description
        "List of NETCONF clients the NETCONF server is
         maintaining simultaneous call-home connections with.";
      uses ncch-oper:ncch-client-oper;
    }
  }
}
