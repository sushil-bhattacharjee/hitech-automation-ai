module Cisco-IOS-XE-port-channel-deviation {
  namespace "http://cisco.com/ns/yang/Cisco-IOS-XE-port-channel-deviation";
  prefix ios-ethernet-p;

  import Cisco-IOS-XE-native {
    prefix ios;
  }
  import Cisco-IOS-XE-ethernet {
    prefix ios-eth;
  }
  import cisco-semver {
    prefix cisco-semver;
  }

  organization
    "Cisco Systems";
  description
    "Cisco XE Native Deviation YANG module for IOS
     Copyright (c) 2020-2021 by Cisco Systems, Inc.
     All rights reserved.";

  revision 2020-11-01 {
    description
      "Added port-channel deviation";
    cisco-semver:module-version "1.1.0";
  }

  deviation "/ios:native/ios:interface/ios:Port-channel/ios:name" {
    deviate replace {
      type uint32 {
        range "1..64";
      }
    }
  }

  deviation "/ios:native/ios:interface/ios:GigabitEthernet/ios-eth:channel-group/ios-eth:number" {
    deviate replace {
      type uint16 {
        range "1..64";
      }
    }
  }

  deviation "/ios:native/ios:interface/ios:AppGigabitEthernet/ios-eth:channel-group/ios-eth:number" {
    deviate replace {
      type uint16 {
        range "1..64";
      }
    }
  }

  deviation "/ios:native/ios:interface/ios:BD-VIF/ios-eth:channel-group/ios-eth:number" {
    deviate replace {
      type uint16 {
        range "1..64";
      }
    }
  }

  deviation "/ios:native/ios:interface/ios:BDI/ios-eth:channel-group/ios-eth:number" {
    deviate replace {
      type uint16 {
        range "1..64";
      }
    }
  }

  deviation "/ios:native/ios:interface/ios:FastEthernet/ios-eth:channel-group/ios-eth:number" {
    deviate replace {
      type uint16 {
        range "1..64";
      }
    }
  }

  deviation "/ios:native/ios:interface/ios:FiveGigabitEthernet/ios-eth:channel-group/ios-eth:number" {
    deviate replace {
      type uint16 {
        range "1..64";
      }
    }
  }

  deviation "/ios:native/ios:interface/ios:FortyGigabitEthernet/ios-eth:channel-group/ios-eth:number" {
    deviate replace {
      type uint16 {
        range "1..64";
      }
    }
  }

  deviation "/ios:native/ios:interface/ios:GigabitEthernet/ios-eth:channel-group/ios-eth:number" {
    deviate replace {
      type uint16 {
        range "1..64";
      }
    }
  }

  deviation "/ios:native/ios:interface/ios:Port-channel/ios-eth:channel-group/ios-eth:number" {
    deviate replace {
      type uint16 {
        range "1..64";
      }
    }
  }

  deviation "/ios:native/ios:interface/ios:Port-channel-subinterface/ios:Port-channel/ios-eth:channel-group/ios-eth:number" {
    deviate replace {
      type uint16 {
        range "1..64";
      }
    }
  }

  deviation "/ios:native/ios:interface/ios:TenGigabitEthernet/ios-eth:channel-group/ios-eth:number" {
    deviate replace {
      type uint16 {
        range "1..64";
      }
    }
  }

  deviation "/ios:native/ios:interface/ios:TwentyFiveGigE/ios-eth:channel-group/ios-eth:number" {
    deviate replace {
      type uint16 {
        range "1..64";
      }
    }
  }

  deviation "/ios:native/ios:interface/ios:TwoGigabitEthernet/ios-eth:channel-group/ios-eth:number" {
    deviate replace {
      type uint16 {
        range "1..64";
      }
    }
  }

  deviation "/ios:native/ios:interface/ios:Virtual-Template/ios-eth:channel-group/ios-eth:number" {
    deviate replace {
      type uint16 {
        range "1..64";
      }
    }
  }

  deviation "/ios:native/ios:interface/ios:VirtualPortGroup/ios-eth:channel-group/ios-eth:number" {
    deviate replace {
      type uint16 {
        range "1..64";
      }
    }
  }

  deviation "/ios:native/ios:interface/ios:Vlan/ios-eth:channel-group/ios-eth:number" {
    deviate replace {
      type uint16 {
        range "1..64";
      }
    }
  }

  deviation "/ios:native/ios:interface/ios:ucse/ios-eth:channel-group/ios-eth:number" {
    deviate replace {
      type uint16 {
        range "1..64";
      }
    }
  }

  deviation "/ios:native/ios:interface/ios:GigabitEthernet/ios-eth:channel-group/ios-eth:mode" {
    deviate replace {
      type enumeration {
        enum active;
        enum passive;
      }
    }
  }

  deviation "/ios:native/ios:interface/ios:AppGigabitEthernet/ios-eth:channel-group/ios-eth:mode" {
    deviate replace {
      type enumeration {
        enum active;
        enum passive;
      }
    }
  }

  deviation "/ios:native/ios:interface/ios:BD-VIF/ios-eth:channel-group/ios-eth:mode" {
    deviate replace {
      type enumeration {
        enum active;
        enum passive;
      }
    }
  }

  deviation "/ios:native/ios:interface/ios:BDI/ios-eth:channel-group/ios-eth:mode" {
    deviate replace {
      type enumeration {
        enum active;
        enum passive;
      }
    }
  }

  deviation "/ios:native/ios:interface/ios:FastEthernet/ios-eth:channel-group/ios-eth:mode" {
    deviate replace {
      type enumeration {
        enum active;
        enum passive;
      }
    }
  }

  deviation "/ios:native/ios:interface/ios:FiveGigabitEthernet/ios-eth:channel-group/ios-eth:mode" {
    deviate replace {
      type enumeration {
        enum active;
        enum passive;
      }
    }
  }

  deviation "/ios:native/ios:interface/ios:FortyGigabitEthernet/ios-eth:channel-group/ios-eth:mode" {
    deviate replace {
      type enumeration {
        enum active;
        enum passive;
      }
    }
  }

  deviation "/ios:native/ios:interface/ios:Port-channel/ios-eth:channel-group/ios-eth:mode" {
    deviate replace {
      type enumeration {
        enum active;
        enum passive;
      }
    }
  }

  deviation "/ios:native/ios:interface/ios:Port-channel-subinterface/ios:Port-channel/ios-eth:channel-group/ios-eth:mode" {
    deviate replace {
      type enumeration {
        enum active;
        enum passive;
      }
    }
  }

  deviation "/ios:native/ios:interface/ios:TenGigabitEthernet/ios-eth:channel-group/ios-eth:mode" {
    deviate replace {
      type enumeration {
        enum active;
        enum passive;
      }
    }
  }

  deviation "/ios:native/ios:interface/ios:TwentyFiveGigE/ios-eth:channel-group/ios-eth:mode" {
    deviate replace {
      type enumeration {
        enum active;
        enum passive;
      }
    }
  }

  deviation "/ios:native/ios:interface/ios:TwoGigabitEthernet/ios-eth:channel-group/ios-eth:mode" {
    deviate replace {
      type enumeration {
        enum active;
        enum passive;
      }
    }
  }

  deviation "/ios:native/ios:interface/ios:Virtual-Template/ios-eth:channel-group/ios-eth:mode" {
    deviate replace {
      type enumeration {
        enum active;
        enum passive;
      }
    }
  }

  deviation "/ios:native/ios:interface/ios:VirtualPortGroup/ios-eth:channel-group/ios-eth:mode" {
    deviate replace {
      type enumeration {
        enum active;
        enum passive;
      }
    }
  }

  deviation "/ios:native/ios:interface/ios:Vlan/ios-eth:channel-group/ios-eth:mode" {
    deviate replace {
      type enumeration {
        enum active;
        enum passive;
      }
    }
  }

  deviation "/ios:native/ios:interface/ios:ucse/ios-eth:channel-group/ios-eth:mode" {
    deviate replace {
      type enumeration {
        enum active;
        enum passive;
      }
    }
  }

  deviation "/ios:native/ios:interface/ios:GigabitEthernet/ios-eth:channel-group/ios-eth:non-silent" {
    deviate not-supported;
  }

  deviation "/ios:native/ios:interface/ios:AppGigabitEthernet/ios-eth:channel-group/ios-eth:non-silent" {
    deviate not-supported;
  }

  deviation "/ios:native/ios:interface/ios:BD-VIF/ios-eth:channel-group/ios-eth:non-silent" {
    deviate not-supported;
  }

  deviation "/ios:native/ios:interface/ios:BDI/ios-eth:channel-group/ios-eth:non-silent" {
    deviate not-supported;
  }

  deviation "/ios:native/ios:interface/ios:FastEthernet/ios-eth:channel-group/ios-eth:non-silent" {
    deviate not-supported;
  }

  deviation "/ios:native/ios:interface/ios:FiveGigabitEthernet/ios-eth:channel-group/ios-eth:non-silent" {
    deviate not-supported;
  }

  deviation "/ios:native/ios:interface/ios:FortyGigabitEthernet/ios-eth:channel-group/ios-eth:non-silent" {
    deviate not-supported;
  }

  deviation "/ios:native/ios:interface/ios:Port-channel/ios-eth:channel-group/ios-eth:non-silent" {
    deviate not-supported;
  }

  deviation "/ios:native/ios:interface/ios:Port-channel-subinterface/ios:Port-channel/ios-eth:channel-group/ios-eth:non-silent" {
    deviate not-supported;
  }

  deviation "/ios:native/ios:interface/ios:TenGigabitEthernet/ios-eth:channel-group/ios-eth:non-silent" {
    deviate not-supported;
  }

  deviation "/ios:native/ios:interface/ios:TwentyFiveGigE/ios-eth:channel-group/ios-eth:non-silent" {
    deviate not-supported;
  }

  deviation "/ios:native/ios:interface/ios:TwoGigabitEthernet/ios-eth:channel-group/ios-eth:non-silent" {
    deviate not-supported;
  }

  deviation "/ios:native/ios:interface/ios:Virtual-Template/ios-eth:channel-group/ios-eth:non-silent" {
    deviate not-supported;
  }

  deviation "/ios:native/ios:interface/ios:VirtualPortGroup/ios-eth:channel-group/ios-eth:non-silent" {
    deviate not-supported;
  }

  deviation "/ios:native/ios:interface/ios:Vlan/ios-eth:channel-group/ios-eth:non-silent" {
    deviate not-supported;
  }

  deviation "/ios:native/ios:interface/ios:ucse/ios-eth:channel-group/ios-eth:non-silent" {
    deviate not-supported;
  }

  deviation "/ios:native/ios:interface/ios:GigabitEthernet/ios-eth:channel-group/ios-eth:auto" {
    deviate not-supported;
  }

  deviation "/ios:native/ios:interface/ios:BD-VIF/ios-eth:channel-group/ios-eth:auto" {
    deviate not-supported;
  }

  deviation "/ios:native/ios:interface/ios:AppGigabitEthernet/ios-eth:channel-group/ios-eth:auto" {
    deviate not-supported;
  }

  deviation "/ios:native/ios:interface/ios:BDI/ios-eth:channel-group/ios-eth:auto" {
    deviate not-supported;
  }

  deviation "/ios:native/ios:interface/ios:FastEthernet/ios-eth:channel-group/ios-eth:auto" {
    deviate not-supported;
  }

  deviation "/ios:native/ios:interface/ios:FiveGigabitEthernet/ios-eth:channel-group/ios-eth:auto" {
    deviate not-supported;
  }

  deviation "/ios:native/ios:interface/ios:FortyGigabitEthernet/ios-eth:channel-group/ios-eth:auto" {
    deviate not-supported;
  }

  deviation "/ios:native/ios:interface/ios:Port-channel/ios-eth:channel-group/ios-eth:auto" {
    deviate not-supported;
  }

  deviation "/ios:native/ios:interface/ios:Port-channel-subinterface/ios:Port-channel/ios-eth:channel-group/ios-eth:auto" {
    deviate not-supported;
  }

  deviation "/ios:native/ios:interface/ios:TenGigabitEthernet/ios-eth:channel-group/ios-eth:auto" {
    deviate not-supported;
  }

  deviation "/ios:native/ios:interface/ios:TwentyFiveGigE/ios-eth:channel-group/ios-eth:auto" {
    deviate not-supported;
  }

  deviation "/ios:native/ios:interface/ios:TwoGigabitEthernet/ios-eth:channel-group/ios-eth:auto" {
    deviate not-supported;
  }

  deviation "/ios:native/ios:interface/ios:Virtual-Template/ios-eth:channel-group/ios-eth:auto" {
    deviate not-supported;
  }

  deviation "/ios:native/ios:interface/ios:VirtualPortGroup/ios-eth:channel-group/ios-eth:auto" {
    deviate not-supported;
  }

  deviation "/ios:native/ios:interface/ios:Vlan/ios-eth:channel-group/ios-eth:auto" {
    deviate not-supported;
  }

  deviation "/ios:native/ios:interface/ios:ucse/ios-eth:channel-group/ios-eth:auto" {
    deviate not-supported;
  }

  deviation "/ios:native/ios:port-channel/ios-eth:load-balance" {
    deviate not-supported;
  }
}
