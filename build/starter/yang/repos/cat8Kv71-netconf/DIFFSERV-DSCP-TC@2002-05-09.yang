/*
 * Generated by confdc --mib2yang-std
 * Source: mgmt/dmi/model/mib/src/DIFFSERV-DSCP-TC.mib
 */
/*
 * This YANG module has been generated by smidump 0.5.0:
 *
 *      smidump -f yang DIFFSERV-DSCP-TC
 *
 * Do not edit. Edit the source file instead!
 */

module DIFFSERV-DSCP-TC {

  namespace "urn:ietf:params:xml:ns:yang:smiv2:DIFFSERV-DSCP-TC";
  prefix DIFFSERV-DSCP-TC;

  import ietf-yang-smiv2 {
    prefix "smiv2";
  }

  organization
   "IETF Differentiated Services WG";

  contact
   "       Fred Baker
    Cisco Systems
    1121 Via Del Rey
    Santa Barbara, CA 93117, USA
    E-mail: fred@cisco.com
    
    Kwok Ho Chan
    Nortel Networks
    600 Technology Park Drive
    Billerica, MA 01821, USA
    E-mail: khchan@nortelnetworks.com
    
    Andrew Smith
    Harbour Networks
    Jiuling Building
    21 North Xisanhuan Ave.
    Beijing, 100089, PRC
    E-mail: ah_smith@acm.org
    
      Differentiated Services Working Group:
      diffserv@ietf.org";

  description
   "The Textual Conventions defined in this module should be used
    whenever a Differentiated Services Code Point is used in a MIB.";

  revision 2002-05-09 {
    description
     "Initial version, published as RFC 3289.";
  }

  typedef Dscp {
    type int32 {
      range "0..63";
    }
    description
     "A Differentiated Services Code-Point that may be used for
      marking a traffic stream.";
    reference
     "RFC 2474, RFC 2780";
    smiv2:display-hint "d";
  }

  typedef DscpOrAny {
    type int32 {
      range "-1..63";
    }
    description
     "The IP header Differentiated Services Code-Point that may be
      
      
      
      used for discriminating among traffic streams. The value -1 is
      used to indicate a wild card i.e. any value.";
    reference
     "RFC 2474, RFC 2780";
    smiv2:display-hint "d";
  }

  smiv2:alias "diffServDSCPTC" {
    smiv2:oid "1.3.6.1.2.1.96";
  }

}
