/*
 * Generated by confdc --mib2yang-std
 * Source: mgmt/dmi/model/mib/src/patched/CISCO-ENTITY-QFP-MIB.mib
 */
/*
 * This YANG module has been generated by smidump 0.5.0:
 *
 *      smidump -f yang CISCO-ENTITY-QFP-MIB
 *
 * Do not edit. Edit the source file instead!
 */

module CISCO-ENTITY-QFP-MIB {

  namespace "urn:ietf:params:xml:ns:yang:smiv2:CISCO-ENTITY-QFP-MIB";
  prefix CISCO-ENTITY-QFP-MIB;

  import ENTITY-MIB {
    prefix "entity-mib";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    
    Postal: 170 W Tasman Drive
    
    San Jose, CA  95134
    
    USA
    
    
    Tel: +1 800 553-NETS
    
    
    E-mail: cs-snmp@cisco.com";

  description
   "This MIB module defines managed objects that facilitate the
    management of Quantum Flow Processors (QFP), which are listed
    in the ENTITY-MIB (RFC 4133) entPhysicalTable as an
    entPhysicalClass of 'cpu'.
    
    The Quantum Flow Processors (QFP) technology is an architecture
    family developed by Cisco, which has fully integrated and
    programmable networking chip set that controls different
    functions of a system such as packet forwarding.
    
    This module contains objects to monitor various QFP
    statistics such as system, utilization, memory, etc.
    
    The utilization statistics can be used for future capacity
    planning. The calculation of this statistics may vary by
    devices which host QFPs, hence the user must refer to the
    specific device document of interest for the exact method
    of calculation. The utilization statistics have the following
    terminology.
    
    o Input - Communication channel where packets arrive on the
              QFP.
    
    o Output - Communication channel where packets leave the QFP.
    
    o Priority - A classification applied to packets indicating
                 they should be treated with greater urgency.
    
    o Non-Priority - A classification applied to packets indicating
                     they should be treated with lesser urgency.
    
    o Processing Load - The percentage of time over some interval
                        that the QFP has spent forwarding packets,
                        relative to the total time spent both 
                        forwarding packets and being idle.";

  revision 2014-06-18 {
    description
     "Added the following objects to the MIB.
      
      ceqfpThroughputLicensedBW, ceqfpThroughputLevel,
      ceqfpThroughputInterval, ceqfpThroughputThreshold,
      ceqfpThroughputAvgRate to ceqfpThroughputTable.
      
      Added ceqfpThroughputNotifEnabled to ciscoEntityQfpNotif group.
      
      Added ceqfpThroughputNotif as a new notification to the MIB.
      
      Added a new MIB conform group, ceqfpThroughputGroup for the new
      objects.
      
      Also modified the ciscoEntityQfpMIBComplianceRev2 to add the new
      group ceqfpThroughputGroup.";
  }

  revision 2012-06-06 {
    description
     "Added the following new objects to the
      ceqfpMemoryResourceTable.
      ceqfpMemoryResTotalOvrflw, ceqfpMemoryHCResTotal,
      ceqfpMemoryResInUseOvrflw, ceqfpMemoryHCResInUse,
      ceqfpMemoryResFreeOvrflw,ceqfpMemoryHCResFree,
      ceqfpMemoryResLowFreeWatermarkOvrflw,
      ceqfpMemoryHCResLowFreeWatermark.
      
      Added following new compliance groups.
      ciscoEntityQfpMemoryResourceOvrflwGroup,
      ciscoEntityQfpMemoryHCResourceGroup.
      
      Added new compliance ciscoEntityQfpMIBComplianceRev2 which
      deprecates ciscoEntityQfpMIBComplianceRev1.";
  }

  revision 2009-12-02 {
    description
     "Initial version of this MIB module.";
  }

  typedef CiscoQfpPacketRate {
    type yang:counter64;
    description
     "An estimate of throughput in units of packets per second.
      
      The CiscoQfpPacketRate type represents a non-negative integer,
      which may increase or decrease, but shall never exceed a 
      maximum value, nor fall below a minimum value of Counter64.
      The Counter64 syntax is used for encoding rules.";
    smiv2:display-hint "d";
  }

  typedef CiscoQfpBitRate {
    type yang:counter64;
    description
     "An estimate of throughput in units of bits per second.
      
      The CiscoQfpBitRate type represents a non-negative integer,
      which may increase or decrease, but shall never exceed a 
      maximum value, nor fall below a minimum value of Counter64.
      The Counter64 syntax is used for encoding rules.";
    smiv2:display-hint "d";
  }

  typedef CiscoQfpTimeInterval {
    type enumeration {
      enum "fiveSeconds" {
        value "1";
      }
      enum "oneMinute" {
        value "2";
      }
      enum "fiveMinutes" {
        value "3";
      }
      enum "sixtyMinutes" {
        value "4";
      }
    }
    description
     "An enumerated integer-value describing the available interval
      values for which the periodic statistics are to be collected.
      
      fiveSeconds (1)   - Interval to collect last 5 seconds       
                          statistics
      oneMinute(2)      - Interval to collect last 1 minute
                          statistics
      fiveMinutes(3)    - Interval to collect last 5 minutes       
                          statistics
      sixtyMinutes(4)   - Interval to collect last 60 minutes       
                          statistics";
  }

  typedef CiscoQfpMemoryResource {
    type enumeration {
      enum "dram" {
        value "1";
      }
    }
    description
     "An enumerated integer-value describing various memory resources
      used by the QFP.
      
      dram (1) - Dynamic Random Access Memory (DRAM) memory resource";
  }


  container CISCO-ENTITY-QFP-MIB {
    config false;

    container ciscoEntityQfp {
      smiv2:oid "1.3.6.1.4.1.9.9.715.1.1";

      leaf ceqfpFiveSecondUtilAlgo {
        type enumeration {
          enum "unknown" {
            value "1";
          }
          enum "fiveSecSample" {
            value "2";
          }
        }
        description
         "This objects represents the method used to calculate 5 Second
          interval utilization data. The enumerated values are described
          below.
          
          unknown       (1) - The calculation method is unknown
          fiveSecSample (2) - The value is calculated based on the last
                              5 second sampling period of utilization
                              data.";
        smiv2:max-access "read-only";
        smiv2:oid "1.3.6.1.4.1.9.9.715.1.1.2";
      }

      leaf ceqfpOneMinuteUtilAlgo {
        type enumeration {
          enum "unknown" {
            value "1";
          }
          enum "fiveSecSMA" {
            value "2";
          }
        }
        description
         "This objects represents the method used to calculate 1 Minute
          interval utilization data. The enumerated values are described
          below.
          
          unknown    (1) - The calculation method is unknown
          fiveSecSMA (2) - The value is calculated using Simple Moving  
                           Average of last 12 five seconds utilization
                           data.";
        smiv2:max-access "read-only";
        smiv2:oid "1.3.6.1.4.1.9.9.715.1.1.3";
      }

      leaf ceqfpFiveMinutesUtilAlgo {
        type enumeration {
          enum "unknown" {
            value "1";
          }
          enum "fiveSecSMA" {
            value "2";
          }
        }
        description
         "This objects represents the method used to calculate 5 Minutes
          interval utilization data. The enumerated values are described
          below.
          
          unknown    (1) - The calculation method is unknown
          fiveSecSMA (2) - The value is calculated using Simple Moving  
                           Average of last 60 five seconds utilization
                           data.";
        smiv2:max-access "read-only";
        smiv2:oid "1.3.6.1.4.1.9.9.715.1.1.4";
      }

      leaf ceqfpSixtyMinutesUtilAlgo {
        type enumeration {
          enum "unknown" {
            value "1";
          }
          enum "fiveSecSMA" {
            value "2";
          }
        }
        description
         "This objects represents the method used to calculate 60 Minutes
          interval utilization data. The enumerated values are described
          below.
          
          unknown    (1) - The calculation method is unknown
          fiveSecSMA (1) - The value is calculated using Simple Moving  
                           Average of last 720 five seconds utilization
                           data.";
        smiv2:max-access "read-only";
        smiv2:oid "1.3.6.1.4.1.9.9.715.1.1.5";
      }
    }

    container ciscoEntityQfpNotif {
      smiv2:oid "1.3.6.1.4.1.9.9.715.1.2";

      leaf ceqfpMemoryResThreshNotifEnabled {
        type boolean;
        description
         "This object controls memory resource rising and falling
          threshold notification.
          
          When this object contains a value 'true', then generation of
          memory resource threshold notification is enabled. If this
          object contains a value 'false', then generation of memory
          resource threshold notification is disabled.";
        smiv2:defval "false";
        smiv2:max-access "read-write";
        smiv2:oid "1.3.6.1.4.1.9.9.715.1.2.1";
      }

      leaf ceqfpThroughputNotifEnabled {
        type uint32 {
          range "0..2";
        }
        description
         "This object controls throughput rate notification.
          
          When this object contains a value 'true', then generation of
          ceqfpThroughputNotif is enabled. If this object contains a value
          'false', then generation of ceqfpThroughputNotif is disabled.";
        smiv2:defval "0";
        smiv2:max-access "read-write";
        smiv2:oid "1.3.6.1.4.1.9.9.715.1.2.4";
      }
    }

    container ceqfpSystemTable {
      description
       "This table maintains the QFP system information for each QFP
        physical entity.
        
        An agent creates a conceptual row to this table corresponding
        to a QFP physical entity upon detection of a physical entity
        supporting the QFP system information.
        
        An agent destroys a conceptual row from this table       
        corresponding to a QFP physical entity upon removal
        of the QFP host physical entity.";
      smiv2:oid "1.3.6.1.4.1.9.9.715.1.1.1";

      list ceqfpSystemEntry {
        key "entPhysicalIndex";
        description
         "A conceptual row in the ceqfpSystemTable. There is an entry
          in this table for each QFP entity, as defined by a value of
          entPhysicalIndex.";
        smiv2:oid "1.3.6.1.4.1.9.9.715.1.1.1.1";

        leaf entPhysicalIndex {
          type leafref {
            path "/entity-mib:ENTITY-MIB/entity-mib:entPhysicalTable/entity-mib:entPhysicalEntry/entity-mib:entPhysicalIndex";
          }
        }

        leaf ceqfpSystemTrafficDirection {
          type enumeration {
            enum "none" {
              value "1";
            }
            enum "ingress" {
              value "2";
            }
            enum "egress" {
              value "3";
            }
            enum "both" {
              value "4";
            }
          }
          description
           "This object represents the traffic direction that this QFP is
            assigned to process. The enumerated values are described below.
            
            none (1)    - The QFP is not assigned to processes any traffic
                          yet
            ingress (2) - The QFP processes inbound traffic
            egress (3)  - The QFP processes outbound traffic
            both (4)    - The QFP processes both inbound and outbound
                          traffic";
          smiv2:max-access "read-only";
          smiv2:oid "1.3.6.1.4.1.9.9.715.1.1.1.1.1";
        }

        leaf ceqfpSystemState {
          type enumeration {
            enum "unknown" {
              value "1";
            }
            enum "reset" {
              value "2";
            }
            enum "init" {
              value "3";
            }
            enum "active" {
              value "4";
            }
            enum "activeSolo" {
              value "5";
            }
            enum "standby" {
              value "6";
            }
            enum "hotStandby" {
              value "7";
            }
          }
          description
           "This object represents the current QFP state. The enumerated
            values are described below.
            
            unknown (1)    - The state of the QFP is unknown
            reset (2)      - The QFP is reset
            init (3)       - The QFP is being initialized
            active (4)     - The QFP is active in a system with redundant
                             QFP
            activeSolo (5) - The QFP is active and there is no redundant
                             QFP in the system
            standby (6)    - The QFP is standby in a redundant system.
            hotStandby (7) - The QFP is standby and synchronized with
                             active, so that a switchover in this state
                             will preserve state of the active. Stateful 
                             datapath features are synchronized between the
                             active QFP and standby QFP";
          smiv2:max-access "read-only";
          smiv2:oid "1.3.6.1.4.1.9.9.715.1.1.1.1.2";
        }

        leaf ceqfpNumberSystemLoads {
          type yang:counter32;
          description
           "This object represents the number of times the QFP is loaded,
            since the QFP host is up.";
          smiv2:max-access "read-only";
          smiv2:oid "1.3.6.1.4.1.9.9.715.1.1.1.1.3";
        }

        leaf ceqfpSystemLastLoadTime {
          type snmpv2-tc:DateAndTime;
          description
           "This object represents the QFP last load time.";
          smiv2:max-access "read-only";
          smiv2:oid "1.3.6.1.4.1.9.9.715.1.1.1.1.4";
        }
      }
    }

    container ceqfpUtilizationTable {
      description
       "This table maintains the utilization statistics collected
        by each QFP physical entity at various time interval such as
        last 5 seconds, 1 minute, etc.
        
        An agent creates a conceptual row to this table corresponding
        to a QFP physical entity for a time interval upon detection of
        a physical entity supporting the utilization statistics for a
        time interval.
        
        The agent destroys a conceptual row from this table       
        corresponding to a QFP physical entity for a time interval
        upon removal of the QFP host physical entity or it does not
        receive the utilization statistics update for a certain time
        period. The time period to wait before deleting an entry from
        this table would be the discretion of the supporting device.";
      smiv2:oid "1.3.6.1.4.1.9.9.715.1.1.6";

      list ceqfpUtilizationEntry {
        key "entPhysicalIndex ceqfpUtilTimeInterval";
        description
         "A conceptual row in the ceqfpUtilizationTable. There is
          an entry in this table for each QFP entity by a value of
          entPhysicalIndex and the supported time interval by a value 
          of ceqfpUtilTimeInterval.
          
          The method of utilization data calculation for each interval
          period can be identified through the respective interval
          scalar objects. For example the utilizaiton data calculation
          method for 'fiveSecond' interval can be identified by
          ceqfpFiveSecondUtilAlgo.";
        smiv2:oid "1.3.6.1.4.1.9.9.715.1.1.6.1";

        leaf entPhysicalIndex {
          type leafref {
            path "/entity-mib:ENTITY-MIB/entity-mib:entPhysicalTable/entity-mib:entPhysicalEntry/entity-mib:entPhysicalIndex";
          }
        }

        leaf ceqfpUtilTimeInterval {
          type CISCO-ENTITY-QFP-MIB:CiscoQfpTimeInterval;
          description
           "This object identifies the time interval for which the
            utilization statistics being collected. The interval 
            values can be 5 second, 1 minute, etc. as specified in 
            the CiscoQfpTimeInterval.";
          smiv2:max-access "not-accessible";
          smiv2:oid "1.3.6.1.4.1.9.9.715.1.1.6.1.1";
        }

        leaf ceqfpUtilInputPriorityPktRate {
          type CISCO-ENTITY-QFP-MIB:CiscoQfpPacketRate;
          units "packets per second";
          description
           "This object represents the QFP input channel priority packet
            rate during this interval.";
          smiv2:max-access "read-only";
          smiv2:oid "1.3.6.1.4.1.9.9.715.1.1.6.1.2";
        }

        leaf ceqfpUtilInputPriorityBitRate {
          type CISCO-ENTITY-QFP-MIB:CiscoQfpBitRate;
          units "bits per second";
          description
           "This object represents the QFP input channel priority bit rate
            during this interval.";
          smiv2:max-access "read-only";
          smiv2:oid "1.3.6.1.4.1.9.9.715.1.1.6.1.3";
        }

        leaf ceqfpUtilInputNonPriorityPktRate {
          type CISCO-ENTITY-QFP-MIB:CiscoQfpPacketRate;
          units "packets per second";
          description
           "This object represents the QFP input channel non-priority
            packet rate during this interval.";
          smiv2:max-access "read-only";
          smiv2:oid "1.3.6.1.4.1.9.9.715.1.1.6.1.4";
        }

        leaf ceqfpUtilInputNonPriorityBitRate {
          type CISCO-ENTITY-QFP-MIB:CiscoQfpBitRate;
          units "bits per second";
          description
           "This object represents the QFP input channel non-priority
            bit rate during this interval.";
          smiv2:max-access "read-only";
          smiv2:oid "1.3.6.1.4.1.9.9.715.1.1.6.1.5";
        }

        leaf ceqfpUtilInputTotalPktRate {
          type CISCO-ENTITY-QFP-MIB:CiscoQfpPacketRate;
          units "packets per second";
          description
           "This object represents the QFP input channel total packet rate
            during this interval, which includes both priority and
            non-priority input packet rate.";
          smiv2:max-access "read-only";
          smiv2:oid "1.3.6.1.4.1.9.9.715.1.1.6.1.6";
        }

        leaf ceqfpUtilInputTotalBitRate {
          type CISCO-ENTITY-QFP-MIB:CiscoQfpBitRate;
          units "bits per second";
          description
           "This object represents the QFP input channel total bit rate
            during this interval, which includes both priority and
            non-priority input bit rate.";
          smiv2:max-access "read-only";
          smiv2:oid "1.3.6.1.4.1.9.9.715.1.1.6.1.7";
        }

        leaf ceqfpUtilOutputPriorityPktRate {
          type CISCO-ENTITY-QFP-MIB:CiscoQfpPacketRate;
          units "packets per second";
          description
           "This object represents the QFP output channel priority packet
            rate during this interval.";
          smiv2:max-access "read-only";
          smiv2:oid "1.3.6.1.4.1.9.9.715.1.1.6.1.8";
        }

        leaf ceqfpUtilOutputPriorityBitRate {
          type CISCO-ENTITY-QFP-MIB:CiscoQfpBitRate;
          units "bits per second";
          description
           "This object represents the QFP output channel priority bit
            rate during this interval.";
          smiv2:max-access "read-only";
          smiv2:oid "1.3.6.1.4.1.9.9.715.1.1.6.1.9";
        }

        leaf ceqfpUtilOutputNonPriorityPktRate {
          type CISCO-ENTITY-QFP-MIB:CiscoQfpPacketRate;
          units "packets per second";
          description
           "This object represents the QFP output channel non-priority
            packet rate during this interval.";
          smiv2:max-access "read-only";
          smiv2:oid "1.3.6.1.4.1.9.9.715.1.1.6.1.10";
        }

        leaf ceqfpUtilOutputNonPriorityBitRate {
          type CISCO-ENTITY-QFP-MIB:CiscoQfpBitRate;
          units "bits per second";
          description
           "This object represents the QFP output channel non-priority
            bit rate during this interval.";
          smiv2:max-access "read-only";
          smiv2:oid "1.3.6.1.4.1.9.9.715.1.1.6.1.11";
        }

        leaf ceqfpUtilOutputTotalPktRate {
          type CISCO-ENTITY-QFP-MIB:CiscoQfpPacketRate;
          units "packets per second";
          description
           "This object represents the QFP output channel total packet rate
            during this interval, which includes both priority and
            non-priority output packet rate.";
          smiv2:max-access "read-only";
          smiv2:oid "1.3.6.1.4.1.9.9.715.1.1.6.1.12";
        }

        leaf ceqfpUtilOutputTotalBitRate {
          type CISCO-ENTITY-QFP-MIB:CiscoQfpBitRate;
          units "bits per second";
          description
           "This object represents the QFP output channel total bit rate
            during this interval, which includes both priority and
            non-priority bit rate.";
          smiv2:max-access "read-only";
          smiv2:oid "1.3.6.1.4.1.9.9.715.1.1.6.1.13";
        }

        leaf ceqfpUtilProcessingLoad {
          type yang:gauge32 {
            range "0..100";
          }
          units "percent";
          description
           "This object represents the QFP processing load during this
            interval.";
          smiv2:max-access "read-only";
          smiv2:oid "1.3.6.1.4.1.9.9.715.1.1.6.1.14";
        }
      }
    }

    container ceqfpMemoryResourceTable {
      description
       "This table maintains the memory resources statistics for
        each QFP physical entity.
        
        An agent creates a conceptual row to this table corresponding
        to a QFP physical entity and its supported memory resource type
        upon detection of a physical entity supporting the memory 
        resource statistics for a memory resource type.
        
        An agent destroys a conceptual row from this table       
        corresponding to a QFP physical entity and its supported
        memory resource type upon removal of the QFP host physical
        entity or it does not receive memory resource statistics
        update for a certain time period. The time period to wait
        before deleting an entry from this table would be the
        discretion of the supporting device.";
      smiv2:oid "1.3.6.1.4.1.9.9.715.1.1.7";

      list ceqfpMemoryResourceEntry {
        key "entPhysicalIndex ceqfpMemoryResType";
        description
         "A conceptual row in the ceqfpMemoryResourceTable. There
          is an entry in this table for each QFP entity by a value 
          of entPhysicalIndex and the supported memory resource type 
          by a value of ceqfpMemoryResType.";
        smiv2:oid "1.3.6.1.4.1.9.9.715.1.1.7.1";

        leaf entPhysicalIndex {
          type leafref {
            path "/entity-mib:ENTITY-MIB/entity-mib:entPhysicalTable/entity-mib:entPhysicalEntry/entity-mib:entPhysicalIndex";
          }
        }

        leaf ceqfpMemoryResType {
          type CISCO-ENTITY-QFP-MIB:CiscoQfpMemoryResource;
          description
           "This object indicates the type of the memory resource used by
            the QFP. This object is one of the indices to uniquely identify
            the QFP memory resource type.";
          smiv2:max-access "not-accessible";
          smiv2:oid "1.3.6.1.4.1.9.9.715.1.1.7.1.1";
        }

        leaf ceqfpMemoryResTotal {
          type yang:gauge32;
          units "kilo bytes";
          description
           "This object represents total memory available on this memory
            resource.";
          smiv2:max-access "read-only";
          smiv2:oid "1.3.6.1.4.1.9.9.715.1.1.7.1.2";
        }

        leaf ceqfpMemoryResInUse {
          type yang:gauge32;
          units "kilo bytes";
          description
           "This object represents the memory which is currently under use
            on this memory resource.";
          smiv2:max-access "read-only";
          smiv2:oid "1.3.6.1.4.1.9.9.715.1.1.7.1.3";
        }

        leaf ceqfpMemoryResFree {
          type yang:gauge32;
          units "kilo bytes";
          description
           "This object represents the memory which is currently free on
            this memory resource.";
          smiv2:max-access "read-only";
          smiv2:oid "1.3.6.1.4.1.9.9.715.1.1.7.1.4";
        }

        leaf ceqfpMemoryResLowFreeWatermark {
          type yang:gauge32;
          units "kilo bytes";
          description
           "This object represents lowest free water mark on this memory
            resource.";
          smiv2:max-access "read-only";
          smiv2:oid "1.3.6.1.4.1.9.9.715.1.1.7.1.5";
        }

        leaf ceqfpMemoryResRisingThreshold {
          type uint32 {
            range "0..100";
          }
          units "percent";
          description
           "This object represents the rising threshold value for this
            memory resource. A value of zero means that the rising
            threshold is not supported for this memory resource.
            
            The value of this object can not be set to lower than or
            equal to ceqfpMemoryResFallingThreshold.
            
            A rising (ceqfpMemoryResRisingThreshNotif) notification
            will be generated, whenever the memory resource usage
            (ceqfpMemoryHCResInUse) is equal to or greater than this
            value.
            
            After a rising notification is generated, another such 
            notification will not be generated until the 
            ceqfpMemoryResInUse falls below this value and reaches 
            the ceqfpMemoryResFallingThreshold.";
          smiv2:defval "90";
          smiv2:max-access "read-write";
          smiv2:oid "1.3.6.1.4.1.9.9.715.1.1.7.1.6";
        }

        leaf ceqfpMemoryResFallingThreshold {
          type uint32 {
            range "0..100";
          }
          units "percent";
          description
           "This object represents the falling threshold value for this
            memory resource. A value of zero means that the falling
            threshold is not supported for this memory resource.
            
            The value of this object can not be set to higher than or
            equal to ceqfpMemoryResRisingThreshold.
            
            A falling (ceqfpMemoryResRisingThreshNotif) notification 
            will be generated, whenever the memory resource usage
            (ceqfpMemoryHCResInUse) is equal to or lesser than this value.
            
            After a falling notification is generated, another 
            such notification will not be generated until the 
            ceqfpMemoryResInUse rises above this value and reaches 
            the ceqfpMemoryResRisingThreshold.";
          smiv2:defval "85";
          smiv2:max-access "read-write";
          smiv2:oid "1.3.6.1.4.1.9.9.715.1.1.7.1.7";
        }

        leaf ceqfpMemoryResTotalOvrflw {
          type yang:gauge32;
          units "kilo bytes";
          description
           "This object represents the upper 32-bit of
            ceqfpMemoryResTotal.
            This object needs to be supported only when the value of
            ceqfpMemoryResTotal exceeds 32-bit, otherwise this object value
            would be set to 0.";
          smiv2:max-access "read-only";
          smiv2:oid "1.3.6.1.4.1.9.9.715.1.1.7.1.8";
        }

        leaf ceqfpMemoryHCResTotal {
          type yang:gauge64;
          units "kilo bytes";
          description
           "This object is a 64-bit version of ceqfpMemoryResTotal.";
          smiv2:max-access "read-only";
          smiv2:oid "1.3.6.1.4.1.9.9.715.1.1.7.1.9";
        }

        leaf ceqfpMemoryResInUseOvrflw {
          type yang:gauge32;
          units "kilo bytes";
          description
           "This object represents the upper 32-bit of
            ceqfpMemoryResInUse.
            This object needs to be supported only when the value of
            ceqfpMemoryResInUse exceeds 32-bit, otherwise this object value
            would be set to 0.";
          smiv2:max-access "read-only";
          smiv2:oid "1.3.6.1.4.1.9.9.715.1.1.7.1.10";
        }

        leaf ceqfpMemoryHCResInUse {
          type yang:gauge64;
          units "kilo bytes";
          description
           "This object is a 64-bit version of ceqfpMemoryInRes.";
          smiv2:max-access "read-only";
          smiv2:oid "1.3.6.1.4.1.9.9.715.1.1.7.1.11";
        }

        leaf ceqfpMemoryResFreeOvrflw {
          type yang:gauge32;
          units "kilo bytes";
          description
           "This object represents the upper 32-bit of ceqfpMemoryResFree.
            This object needs to be supported only when the value of
            ceqfpMemoryResFree exceeds 32-bit, otherwise this object value
            would be set to 0.";
          smiv2:max-access "read-only";
          smiv2:oid "1.3.6.1.4.1.9.9.715.1.1.7.1.12";
        }

        leaf ceqfpMemoryHCResFree {
          type yang:gauge64;
          units "kilo bytes";
          description
           "This object is a 64-bit version of ceqfpMemoryResFree.";
          smiv2:max-access "read-only";
          smiv2:oid "1.3.6.1.4.1.9.9.715.1.1.7.1.13";
        }

        leaf ceqfpMemoryResLowFreeWatermarkOvrflw {
          type yang:gauge32;
          units "kilo bytes";
          description
           "This object represents the upper 32-bit of
            ceqfpMemoryResLowFreeWatermark. This object needs to be
            supported only when the value of ceqfpMemoryResLowFreeWatermark
            exceeds 32-bit, otherwise this object value would be set to 0.";
          smiv2:max-access "read-only";
          smiv2:oid "1.3.6.1.4.1.9.9.715.1.1.7.1.14";
        }

        leaf ceqfpMemoryHCResLowFreeWatermark {
          type yang:gauge64;
          units "kilo bytes";
          description
           "This object is a 64-bit version of
            ceqfpMemoryResLowFreeWatermark.";
          smiv2:max-access "read-only";
          smiv2:oid "1.3.6.1.4.1.9.9.715.1.1.7.1.15";
        }
      }
    }

    container ceqfpThroughputTable {
      description
       "This table maintains the throughput information for each
        QFP physical entity.
        
                An agent creates a conceptual row to this table
        corresponding to a QFP physical entity upon detection of a
        physical entity supporting the QFP throughput information.
        
                An agent destroys a conceptual row from this table     
        
        corresponding to a QFP physical entity upon removal of the QFP
        host physical entity.";
      smiv2:oid "1.3.6.1.4.1.9.9.715.1.1.8";

      list ceqfpThroughputEntry {
        key "entPhysicalIndex";
        description
         "A conceptual row in the ceqfpThroughputTable. There is an entry
          in this table for each QFP entity, as defined by a value of
          entPhysicalIndex.";
        smiv2:oid "1.3.6.1.4.1.9.9.715.1.1.8.1";

        leaf entPhysicalIndex {
          type leafref {
            path "/entity-mib:ENTITY-MIB/entity-mib:entPhysicalTable/entity-mib:entPhysicalEntry/entity-mib:entPhysicalIndex";
          }
        }

        leaf ceqfpThroughputLicensedBW {
          type yang:counter64;
          units "bits per second";
          description
           "This object represents the bandwidth for installed
            throughput license.";
          smiv2:max-access "read-only";
          smiv2:oid "1.3.6.1.4.1.9.9.715.1.1.8.1.1";
        }

        leaf ceqfpThroughputLevel {
          type enumeration {
            enum "normal" {
              value "1";
            }
            enum "warning" {
              value "2";
            }
            enum "exceed" {
              value "3";
            }
          }
          description
           "This object represents the current throughput level for
            installed throughput license.
            
                            normal  (1) - Throughput usage is normal
                            warning (2) - Throughput usage has crossed the
                                          configured threshold limit
                            exceed  (3) - Throughput usage has exceeded the
                                          total licensed bandwidth";
          smiv2:max-access "read-only";
          smiv2:oid "1.3.6.1.4.1.9.9.715.1.1.8.1.2";
        }

        leaf ceqfpThroughputInterval {
          type int32 {
            range "10..86400";
          }
          units "seconds";
          description
           "The object represents the configured time interval at which the
            ceqfpThroughputLevel is checked.";
          smiv2:max-access "read-write";
          smiv2:oid "1.3.6.1.4.1.9.9.715.1.1.8.1.3";
        }

        leaf ceqfpThroughputThreshold {
          type int32 {
            range "75..95";
          }
          units "percent";
          description
           "The object represents the configured throughput threshold.";
          smiv2:max-access "read-write";
          smiv2:oid "1.3.6.1.4.1.9.9.715.1.1.8.1.4";
        }

        leaf ceqfpThroughputAvgRate {
          type yang:counter64;
          units "bits per second";
          description
           "The object represents the average throughput rate in the
            interval ceqfpThroughputInterval.";
          smiv2:max-access "read-only";
          smiv2:oid "1.3.6.1.4.1.9.9.715.1.1.8.1.5";
        }
      }
    }
  }

  notification ceqfpMemoryResRisingThreshNotif {
    description
     "A notification indicating that the QFP memory usage is rising
      the threshold on this memory resource.
      
      This notification will be sent, whenever the QFP memory
      usage (ceqfpMemoryResInUse) is equal to or above the 
      rising threshold (ceqfpMemoryResRisingThreshold).
      
      An agent may throttle the generation of consecutive
      ceqfpMemoryResRisingThreshNotif notification so that
      there is at least a five second (suggested default)
      gap between notification of this type.";
    smiv2:oid "1.3.6.1.4.1.9.9.715.0.1";

    container object-1 {

      leaf entPhysicalIndex {
        type leafref {
          path "/entity-mib:ENTITY-MIB/entity-mib:entPhysicalTable/entity-mib:entPhysicalEntry/entity-mib:entPhysicalIndex";
        }
      }

      leaf ceqfpMemoryResType {
        type leafref {
          path "/CISCO-ENTITY-QFP-MIB:CISCO-ENTITY-QFP-MIB/CISCO-ENTITY-QFP-MIB:ceqfpMemoryResourceTable/CISCO-ENTITY-QFP-MIB:ceqfpMemoryResourceEntry/CISCO-ENTITY-QFP-MIB:ceqfpMemoryResType";
        }
      }

      leaf ceqfpMemoryResInUse {
        type leafref {
          path "/CISCO-ENTITY-QFP-MIB:CISCO-ENTITY-QFP-MIB/CISCO-ENTITY-QFP-MIB:ceqfpMemoryResourceTable/CISCO-ENTITY-QFP-MIB:ceqfpMemoryResourceEntry/CISCO-ENTITY-QFP-MIB:ceqfpMemoryResInUse";
        }
      }
    }

    container object-2 {

      leaf ceqfpMemoryResCurrentRisingThresh {
        type uint32 {
          range "1..100";
        }
        units "percent";
        description
         "This object represents the current rising threshold
          value, which triggers the rising threshold notification
          (ceqfpMemoryResRisingThreshNotif).";
        smiv2:max-access "accessible-for-notify";
        smiv2:oid "1.3.6.1.4.1.9.9.715.1.2.2";
      }
    }
  }

  notification ceqfpMemoryResFallingThreshNotif {
    description
     "A notification indicating that the QFP memory usage is equal
      to or below the falling threshold on this memory resource.
      
      This notification will be sent, whenever the QFP memory
      usage (ceqfpMemoryResInUse) is equal to or below the 
      falling threshold (ceqfpMemoryResFallingThreshold).
      
      An agent may throttle the generation of consecutive
      ceqfpMemoryResFallingThreshNotif notification so that
      there is at least a five second (suggested default)
      gap between notification of this type.";
    smiv2:oid "1.3.6.1.4.1.9.9.715.0.2";

    container object-1 {

      leaf entPhysicalIndex {
        type leafref {
          path "/entity-mib:ENTITY-MIB/entity-mib:entPhysicalTable/entity-mib:entPhysicalEntry/entity-mib:entPhysicalIndex";
        }
      }

      leaf ceqfpMemoryResType {
        type leafref {
          path "/CISCO-ENTITY-QFP-MIB:CISCO-ENTITY-QFP-MIB/CISCO-ENTITY-QFP-MIB:ceqfpMemoryResourceTable/CISCO-ENTITY-QFP-MIB:ceqfpMemoryResourceEntry/CISCO-ENTITY-QFP-MIB:ceqfpMemoryResType";
        }
      }

      leaf ceqfpMemoryResInUse {
        type leafref {
          path "/CISCO-ENTITY-QFP-MIB:CISCO-ENTITY-QFP-MIB/CISCO-ENTITY-QFP-MIB:ceqfpMemoryResourceTable/CISCO-ENTITY-QFP-MIB:ceqfpMemoryResourceEntry/CISCO-ENTITY-QFP-MIB:ceqfpMemoryResInUse";
        }
      }
    }

    container object-2 {

      leaf ceqfpMemoryResCurrentFallingThresh {
        type uint32;
        units "percent";
        description
         "This object represents the current falling threshold
          value, which triggers the falling threshold notification
          (ceqfpMemoryResFallingThreshNotif).";
        smiv2:max-access "accessible-for-notify";
        smiv2:oid "1.3.6.1.4.1.9.9.715.1.2.3";
      }
    }
  }

  notification ceqfpThroughputNotif {
    description
     "A notification indicating that the average throughput rate for
      the configured interval has exceeded the threshold or reached
      maximum bandwidth allowed.
      
      This notification will be sent, whenever the ceqfpThroughputLevel
      object has the value warning(2) or exceed(3). The condition for
      trap generation will be checked in every
      ceqfpThroughputInterval.
      
      ceqfpThroughputNotif with ceqfpThrougputLevel as warning(2)
      indicates that average throughput rate has crossed the
      configured threshold.
      
      ceqfpThroughputNotif with ceqfpThrougputLevel as exceed(3)
      indicates that average throughput rate has reached maximum
      licensed bandwidth.";
    smiv2:oid "1.3.6.1.4.1.9.9.715.0.3";

    container object-1 {

      leaf entPhysicalIndex {
        type leafref {
          path "/entity-mib:ENTITY-MIB/entity-mib:entPhysicalTable/entity-mib:entPhysicalEntry/entity-mib:entPhysicalIndex";
        }
      }

      leaf ceqfpThroughputLicensedBW {
        type leafref {
          path "/CISCO-ENTITY-QFP-MIB:CISCO-ENTITY-QFP-MIB/CISCO-ENTITY-QFP-MIB:ceqfpThroughputTable/CISCO-ENTITY-QFP-MIB:ceqfpThroughputEntry/CISCO-ENTITY-QFP-MIB:ceqfpThroughputLicensedBW";
        }
      }
    }

    container object-2 {

      leaf entPhysicalIndex {
        type leafref {
          path "/entity-mib:ENTITY-MIB/entity-mib:entPhysicalTable/entity-mib:entPhysicalEntry/entity-mib:entPhysicalIndex";
        }
      }

      leaf ceqfpThroughputLevel {
        type leafref {
          path "/CISCO-ENTITY-QFP-MIB:CISCO-ENTITY-QFP-MIB/CISCO-ENTITY-QFP-MIB:ceqfpThroughputTable/CISCO-ENTITY-QFP-MIB:ceqfpThroughputEntry/CISCO-ENTITY-QFP-MIB:ceqfpThroughputLevel";
        }
      }
    }

    container object-3 {

      leaf entPhysicalIndex {
        type leafref {
          path "/entity-mib:ENTITY-MIB/entity-mib:entPhysicalTable/entity-mib:entPhysicalEntry/entity-mib:entPhysicalIndex";
        }
      }

      leaf ceqfpThroughputAvgRate {
        type leafref {
          path "/CISCO-ENTITY-QFP-MIB:CISCO-ENTITY-QFP-MIB/CISCO-ENTITY-QFP-MIB:ceqfpThroughputTable/CISCO-ENTITY-QFP-MIB:ceqfpThroughputEntry/CISCO-ENTITY-QFP-MIB:ceqfpThroughputAvgRate";
        }
      }
    }
  }

  smiv2:alias "ciscoEntityQfpMIB" {
    smiv2:oid "1.3.6.1.4.1.9.9.715";
  }

  smiv2:alias "ciscoEntityQfpMIBNotifs" {
    smiv2:oid "1.3.6.1.4.1.9.9.715.0";
  }

  smiv2:alias "ciscoEntityQfpMIBObjects" {
    smiv2:oid "1.3.6.1.4.1.9.9.715.1";
  }

  smiv2:alias "ciscoEntityQfp" {
    smiv2:oid "1.3.6.1.4.1.9.9.715.1.1";
  }

  smiv2:alias "ciscoEntityQfpNotif" {
    smiv2:oid "1.3.6.1.4.1.9.9.715.1.2";
  }

  smiv2:alias "ciscoEntityQfpMIBConform" {
    smiv2:oid "1.3.6.1.4.1.9.9.715.2";
  }

  smiv2:alias "ciscoEntityQfpMIBCompliances" {
    smiv2:oid "1.3.6.1.4.1.9.9.715.2.1";
  }

  smiv2:alias "ciscoEntityQfpMIBGroups" {
    smiv2:oid "1.3.6.1.4.1.9.9.715.2.2";
  }

}
