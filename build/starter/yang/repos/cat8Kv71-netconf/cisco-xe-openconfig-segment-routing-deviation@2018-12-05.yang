module cisco-xe-openconfig-segment-routing-deviation {
  namespace "http://cisco.com/ns/cisco-xe-openconfig-segment-routing-deviation";
  prefix oc-segment-routing-devs;

  import openconfig-network-instance {
    prefix oc-netinst;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-segment-routing module.";

  revision 2018-12-05 {
    description
      "Initial Revision";
  }

  deviation "/oc-netinst:network-instances/oc-netinst:network-instance/oc-netinst:segment-routing" {
    deviate not-supported;
    description
      "Not supported in 16.12 release";
  }
}
