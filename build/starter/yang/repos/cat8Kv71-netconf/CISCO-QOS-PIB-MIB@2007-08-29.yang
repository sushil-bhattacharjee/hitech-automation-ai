/*
 * Generated by confdc --mib2yang-std
 * Source: mgmt/dmi/model/mib/src/CISCO-QOS-PIB-MIB.mib
 */
/*
 * This YANG module has been generated by smidump 0.5.0:
 *
 *      smidump -f yang CISCO-QOS-PIB-MIB
 *
 * Do not edit. Edit the source file instead!
 */

module CISCO-QOS-PIB-MIB {

  namespace "urn:ietf:params:xml:ns:yang:smiv2:CISCO-QOS-PIB-MIB";
  prefix CISCO-QOS-PIB-MIB;

  import SNMPv2-TC {
    prefix "snmpv2-tc";
  }

  import ietf-inet-types {
    prefix "inet";
  }

  import ietf-yang-smiv2 {
    prefix "smiv2";
  }

  import ietf-yang-types {
    prefix "yang";
  }

  organization
   "Cisco Systems Inc.";

  contact
   "Cisco Systems
    Customer Service
    
    Postal: 170 W Tasman Drive
        San Jose, CA 95134
        USA
    
    Tel: +1 800 553-NETS
    
    E-mail: cs-wbu@cisco.com";

  description
   "The Cisco QOS Policy PIB for provisioning QOS policy.";

  revision 2007-08-29 {
    description
     "Add new enum values in QosInterfaceQueueType
      textual convention for various queue type.";
  }

  revision 2004-05-03 {
    description
     "Add new enum value in QosInterfaceQueueType
      textual convention for 1p3q8t queue type.";
  }

  revision 2003-02-21 {
    description
     "Add new enum values in QosInterfaceQueueType
      textual convention to indicate queue types
      containing priority queue. Add new enum value
      in ThresholdSetRange textual convention for
      zero threshold.";
  }

  revision 2002-05-02 {
    description
     "Fix the SYNTAX of Role and RoleCombination.";
  }

  revision 2000-06-16 {
    description
     "Added QosInterfaceTypeCapabilities textual convention.";
  }

  revision 2000-05-11 {
    description
     "Initial version of this PIB module.";
  }

  typedef Dscp {
    type int32 {
      range "0..63";
    }
    description
     "An integer that is in the range of the DiffServ codepoint
      values.";
  }

  typedef QosLayer2Cos {
    type int32 {
      range "0..7";
    }
    description
     "An integer that is in the range of the layer 2 CoS values.
      This corresponds to the 802.1p and ISL CoS values.";
  }

  typedef QueueRange {
    type enumeration {
      enum "oneQ" {
        value "1";
      }
      enum "twoQ" {
        value "2";
      }
      enum "threeQ" {
        value "3";
      }
      enum "fourQ" {
        value "4";
      }
      enum "eightQ" {
        value "8";
      }
      enum "sixteenQ" {
        value "16";
      }
      enum "thirtyTwoQ" {
        value "32";
      }
      enum "sixtyFourQ" {
        value "64";
      }
    }
    description
     "An integer that is limited to the number of queues per
      interface supported by the PIB.  Limited to 64 which is the
      number of codepoints.";
  }

  typedef ThresholdSetRange {
    type enumeration {
      enum "zeroT" {
        value "0";
      }
      enum "oneT" {
        value "1";
      }
      enum "twoT" {
        value "2";
      }
      enum "fourT" {
        value "4";
      }
      enum "eightT" {
        value "8";
      }
    }
    description
     "An integer that is limited to the number of threshold sets
      per queue supported by the PIB. A threshold set is a
      collection of parameters describing queue threshold.  The
      parameters of a threshold set depend on the drop mechanism the
      queue implements.  For example, the threshold set for
      tail-drop  comprises a single parameter, the percentage of
      queue size at which dropping occurs.  The threshold set for
      WRED comprises two parameters; within the range of the two
      parameters packets are randomly dropped.";
  }

  typedef Percent {
    type int32 {
      range "0..100";
    }
    description
     "An integer that is in the range of a percent value.";
  }

  typedef QosInterfaceQueueType {
    type enumeration {
      enum "oneQ1t" {
        value "1";
      }
      enum "oneQ2t" {
        value "2";
      }
      enum "oneQ4t" {
        value "3";
      }
      enum "oneQ8t" {
        value "4";
      }
      enum "twoQ1t" {
        value "5";
      }
      enum "twoQ2t" {
        value "6";
      }
      enum "twoQ4t" {
        value "7";
      }
      enum "twoQ8t" {
        value "8";
      }
      enum "threeQ1t" {
        value "9";
      }
      enum "threeQ2t" {
        value "10";
      }
      enum "threeQ4t" {
        value "11";
      }
      enum "threeQ8t" {
        value "12";
      }
      enum "fourQ1t" {
        value "13";
      }
      enum "fourQ2t" {
        value "14";
      }
      enum "fourQ4t" {
        value "15";
      }
      enum "fourQ8t" {
        value "16";
      }
      enum "eightQ1t" {
        value "17";
      }
      enum "eightQ2t" {
        value "18";
      }
      enum "eightQ4t" {
        value "19";
      }
      enum "eightQ8t" {
        value "20";
      }
      enum "sixteenQ1t" {
        value "21";
      }
      enum "sixteenQ2t" {
        value "22";
      }
      enum "sixteenQ4t" {
        value "23";
      }
      enum "sixtyfourQ1t" {
        value "24";
      }
      enum "sixtyfourQ2t" {
        value "25";
      }
      enum "sixtyfourQ4t" {
        value "26";
      }
      enum "oneP1Q0t" {
        value "27";
      }
      enum "oneP1Q4t" {
        value "28";
      }
      enum "oneP1Q8t" {
        value "29";
      }
      enum "oneP2Q1t" {
        value "30";
      }
      enum "oneP2Q2t" {
        value "31";
      }
      enum "oneP3Q1t" {
        value "32";
      }
      enum "oneP7Q8t" {
        value "33";
      }
      enum "oneP3Q8t" {
        value "34";
      }
      enum "sixteenQ8t" {
        value "35";
      }
      enum "oneP15Q8t" {
        value "36";
      }
      enum "oneP15Q1t" {
        value "37";
      }
      enum "oneP7Q1t" {
        value "38";
      }
      enum "oneP31Q1t" {
        value "39";
      }
      enum "thirtytwoQ1t" {
        value "40";
      }
      enum "thirtytwoQ8t" {
        value "41";
      }
      enum "oneP31Q8t" {
        value "42";
      }
      enum "oneP7Q4t" {
        value "43";
      }
      enum "oneP3Q4t" {
        value "44";
      }
      enum "oneP7Q2t" {
        value "45";
      }
    }
    description
     "An enumerated type for all the known interface types.  The
      interface types are currently limited to a predefined
      combination of queues and thresholds such that the product of
      queues and thresholds does not exceed 64 (i.e., the total
      number of DSCPs.";
  }

  typedef QosInterfaceTypeCapabilities {
    type bits {
      bit unspecified {
        position "0";
      }
      bit inputL2Classification {
        position "1";
      }
      bit inputIpClassification {
        position "2";
      }
      bit outputL2Classification {
        position "3";
      }
      bit outputIpClassification {
        position "4";
      }
      bit inputUflowPolicing {
        position "5";
      }
      bit inputAggregatePolicing {
        position "6";
      }
      bit outputUflowPolicing {
        position "7";
      }
      bit outputAggregatePolicing {
        position "8";
      }
      bit policeByMarkingDown {
        position "9";
      }
      bit policeByDropping {
        position "10";
      }
      bit fifo {
        position "11";
      }
      bit wrr {
        position "12";
      }
      bit wfq {
        position "13";
      }
      bit cq {
        position "14";
      }
      bit pq {
        position "15";
      }
      bit cbwfq {
        position "16";
      }
      bit tailDrop {
        position "17";
      }
      bit wred {
        position "18";
      }
      bit inputPortClassification {
        position "19";
      }
      bit outputPortClassification {
        position "20";
      }
      bit inputUflowShaping {
        position "21";
      }
      bit inputAggregateShaping {
        position "22";
      }
      bit outputUflowShaping {
        position "23";
      }
      bit outputAggregateShaping {
        position "24";
      }
      bit pqWrr {
        position "25";
      }
      bit pqCbwfq {
        position "26";
      }
    }
    description
     "An enumeration of interface capabilities.  Used by the PDP to
      select policies and configuration to push to the PEP.";
  }

  typedef RoleCombination {
    type binary {
      length "0..255";
    }
    description
     "A Display string consisting of a set of roles concatenated
      with a '+' character where the roles are in lexicographic
      order from minimum to maximum.";
  }

  typedef PolicyInstanceId {
    type uint32;
    description
     "A textual convention for an attribute that is an an
      unsigned integer index attribute of class.  It is used for
      attributes that exist for the purpose of providing an integer
      index of an instance.
      
      For any integer index that refers to another policy instance,
      that other policy instance must exist. Furthermore, it is an
      error to try to delete a policy instance that is referred to by
      another instance without first deleting the referring
      instance.";
  }


  container CISCO-QOS-PIB-MIB {
    config false;

    container qosDevicePibIncarnationTable {
      description
       "This class contains a single policy instance that identifies
        the current incarnation of the PIB and the PDP that installed
        this incarnation.  The instance of this class is reported to
        the PDP at client connect time so that the PDP can (attempt
        to) ascertain the current state of the PIB.";
      smiv2:oid "1.3.6.1.4.1.9.18.2.1.2.1";

      list qosDevicePibIncarnationEntry {
        key "qosDeviceIncarnationId";
        description
         "The single policy instance of this class identifies the
          current incarnation of the PIB and the PDP that installed
          this incarnation.";
        smiv2:oid "1.3.6.1.4.1.9.18.2.1.2.1.1";

        leaf qosDeviceIncarnationId {
          type CISCO-QOS-PIB-MIB:PolicyInstanceId;
          description
           "An integer index to identify the instance of the policy class.";
          smiv2:max-access "not-accessible";
          smiv2:oid "1.3.6.1.4.1.9.18.2.1.2.1.1.1";
        }

        leaf qosDevicePdpName {
          type snmpv2-tc:DisplayString;
          description
           "The name of the PDP that installed the current incarnation of
            the PIB into the device.  By default it is the zero length
            string.";
          smiv2:max-access "read-only";
          smiv2:oid "1.3.6.1.4.1.9.18.2.1.2.1.1.2";
        }

        leaf qosDevicePibIncarnation {
          type binary {
            length "128";
          }
          description
           "An octet string to identify the current incarnation.  It has
            meaning to the PDP that installed the PIB and perhaps its
            standby PDPs. By default the empty string.";
          smiv2:max-access "read-only";
          smiv2:oid "1.3.6.1.4.1.9.18.2.1.2.1.1.3";
        }

        leaf qosDevicePibTtl {
          type uint32;
          description
           "The number of seconds after a client close or TCP timeout for
            which the PEP continues to enforce the policy in the PIB.
            After this interval, the PIB is consired expired and the
            device no longer enforces the policy installed in the PIB.";
          smiv2:max-access "read-only";
          smiv2:oid "1.3.6.1.4.1.9.18.2.1.2.1.1.4";
        }
      }
    }

    container qosDeviceAttributeTable {
      description
       "The single instance of this class indicates specific
        attributes of the device.  These include configuration values
        such as the configured PDP addresses, the maximum message
        size, and specific device capabilities.  The latter include
        input port-based and output port-based classification and/or
        policing, support for flow based policing, aggregate based
        policing, traffic shaping capabilities, etc.";
      smiv2:oid "1.3.6.1.4.1.9.18.2.1.2.2";

      list qosDeviceAttributeEntry {
        key "qosDeviceAttributeId";
        description
         "The single instance of this class indicates specific
          attributes of the device.";
        smiv2:oid "1.3.6.1.4.1.9.18.2.1.2.2.1";

        leaf qosDeviceAttributeId {
          type CISCO-QOS-PIB-MIB:PolicyInstanceId;
          description
           "An integer index to identify the instance of the policy class.";
          smiv2:max-access "not-accessible";
          smiv2:oid "1.3.6.1.4.1.9.18.2.1.2.2.1.1";
        }

        leaf qosDevicePepDomain {
          type snmpv2-tc:DisplayString;
          description
           "The QoS domain that this device belongs to.  This is
            configured locally on the device (perhaps by some management
            protocol such as SNMP).  By default, it is the zero-length
            string.";
          smiv2:max-access "read-only";
          smiv2:oid "1.3.6.1.4.1.9.18.2.1.2.2.1.2";
        }

        leaf qosDevicePrimaryPdp {
          type inet:ipv4-address;
          description
           "The address of the PDP configured to be the primary PDP for
            the device.";
          smiv2:max-access "read-only";
          smiv2:oid "1.3.6.1.4.1.9.18.2.1.2.2.1.3";
        }

        leaf qosDeviceSecondaryPdp {
          type inet:ipv4-address;
          description
           "The address of the PDP configured to be the secondary PDP for
            the device.  An address of zero indicates no secondary is
            configured.";
          smiv2:max-access "read-only";
          smiv2:oid "1.3.6.1.4.1.9.18.2.1.2.2.1.4";
        }

        leaf qosDeviceMaxMessageSize {
          type uint32;
          description
           "The maximum size message that this PEP is capable of
            receiving in bytes.  A value of zero means that the maximum
            message size is unspecified (but does not mean it is
            unlimited).  A message greater than this maximum results in a
            MessageTooBig error on a 'no commit' REP.";
          smiv2:max-access "read-only";
          smiv2:oid "1.3.6.1.4.1.9.18.2.1.2.2.1.5";
        }

        leaf qosDeviceCapabilities {
          type bits {
            bit unspecified {
              position "0";
            }
            bit layer2Cos {
              position "1";
            }
            bit ipPrecedence {
              position "2";
            }
            bit dscp {
              position "3";
            }
          }
          description
           "An enumeration of device capabilities.  Used by the PDP to
            select policies and configuration to push to the PEP.";
          smiv2:max-access "read-only";
          smiv2:oid "1.3.6.1.4.1.9.18.2.1.2.2.1.6";
        }
      }
    }

    container qosInterfaceTypeTable {
      description
       "This class describes the interface types of the interfaces
        that exist on the device.  It includes the queue type, role
        combination and capabilities of interfaces.  The PEP does not
        report which specific interfaces have which characteristics.";
      smiv2:oid "1.3.6.1.4.1.9.18.2.1.2.3";

      list qosInterfaceTypeEntry {
        key "qosInterfaceTypeId";
        description
         "An instance of this class describes a role combination for
          an interface type of an interface that exists on the device.";
        smiv2:oid "1.3.6.1.4.1.9.18.2.1.2.3.1";

        leaf qosInterfaceTypeId {
          type CISCO-QOS-PIB-MIB:PolicyInstanceId;
          description
           "An integer index to identify the instance of the policy class.";
          smiv2:max-access "not-accessible";
          smiv2:oid "1.3.6.1.4.1.9.18.2.1.2.3.1.1";
        }

        leaf qosInterfaceQueueType {
          type CISCO-QOS-PIB-MIB:QosInterfaceQueueType;
          description
           "The interface type in terms of number of queues and
            thresholds.";
          smiv2:max-access "read-only";
          smiv2:oid "1.3.6.1.4.1.9.18.2.1.2.3.1.2";
        }

        leaf qosInterfaceTypeRoles {
          type CISCO-QOS-PIB-MIB:RoleCombination;
          description
           "A combination of roles on at least one interface of type
            qosInterfaceType.";
          smiv2:max-access "read-only";
          smiv2:oid "1.3.6.1.4.1.9.18.2.1.2.3.1.3";
        }

        leaf qosInterfaceTypeCapabilities {
          type CISCO-QOS-PIB-MIB:QosInterfaceTypeCapabilities;
          description
           "An enumeration of interface capabilities.  Used by the PDP to
            select policies and configuration to push to the PEP.";
          smiv2:max-access "read-only";
          smiv2:oid "1.3.6.1.4.1.9.18.2.1.2.3.1.4";
        }
      }
    }

    container qosDiffServMappingTable {
      description
       "Maps each DSCP to a marked-down DSCP.  Also maps each DSCP to
        an IP precedence and QosLayer2Cos.  When configured for the
        first time, all 64 entries of the table must be
        specified. Thereafter, instances may be modified (with a
        delete and install in a single decision) but not deleted
        unless all instances are deleted.";
      smiv2:oid "1.3.6.1.4.1.9.18.2.1.3.1";

      list qosDiffServMappingEntry {
        key "qosDscp";
        description
         "An instance of this class represents mappings from a DSCP.";
        smiv2:oid "1.3.6.1.4.1.9.18.2.1.3.1.1";

        leaf qosDscp {
          type CISCO-QOS-PIB-MIB:Dscp;
          description
           "A DSCP for which this entry contains mappings.";
          smiv2:max-access "not-accessible";
          smiv2:oid "1.3.6.1.4.1.9.18.2.1.3.1.1.1";
        }

        leaf qosMarkedDscp {
          type CISCO-QOS-PIB-MIB:Dscp;
          description
           "The DSCP to use instead of the qosDscp when the packet is out
            of profile and hence marked as such.";
          smiv2:max-access "read-only";
          smiv2:oid "1.3.6.1.4.1.9.18.2.1.3.1.1.2";
        }

        leaf qosL2Cos {
          type CISCO-QOS-PIB-MIB:QosLayer2Cos;
          description
           "The L2 CoS value to use when mapping this DSCP to layer 2
            CoS.";
          smiv2:max-access "read-only";
          smiv2:oid "1.3.6.1.4.1.9.18.2.1.3.1.1.3";
        }
      }
    }

    container qosCosToDscpTable {
      description
       "Maps each of eight CoS values to a DSCP.  When configured for
        the first time, all 8 entries of the table must be
        specified. Thereafter, instances may be modified (with a
        delete and install in a single decision) but not deleted
        unless all instances are deleted.";
      smiv2:oid "1.3.6.1.4.1.9.18.2.1.3.2";

      list qosCosToDscpEntry {
        key "qosCosToDscpCos";
        description
         "An instance of this class maps a CoS value to a DSCP.";
        smiv2:oid "1.3.6.1.4.1.9.18.2.1.3.2.1";

        leaf qosCosToDscpCos {
          type CISCO-QOS-PIB-MIB:QosLayer2Cos;
          description
           "The L2 CoS value that is being mapped.";
          smiv2:max-access "not-accessible";
          smiv2:oid "1.3.6.1.4.1.9.18.2.1.3.2.1.1";
        }

        leaf qosCosToDscpDscp {
          type CISCO-QOS-PIB-MIB:Dscp;
          description
           "The DSCP value to use when mapping the L2 CoS to a DSCP.";
          smiv2:max-access "read-only";
          smiv2:oid "1.3.6.1.4.1.9.18.2.1.3.2.1.2";
        }
      }
    }

    container qosUnmatchedPolicyTable {
      description
       "A policy class that specifies what QoS to apply to a packet
        that does not match any other policy configured for this role
        combination for a particular direction of traffic.";
      smiv2:oid "1.3.6.1.4.1.9.18.2.1.4.1";

      list qosUnmatchedPolicyEntry {
        key "qosUnmatchedPolicyId";
        description
         "An instance of this class specifies the unmatched policy
          for a particular role combination for incoming or outgoing
          traffic.";
        smiv2:oid "1.3.6.1.4.1.9.18.2.1.4.1.1";

        leaf qosUnmatchedPolicyId {
          type CISCO-QOS-PIB-MIB:PolicyInstanceId;
          description
           "An integer index to identify the instance of the policy class.";
          smiv2:max-access "not-accessible";
          smiv2:oid "1.3.6.1.4.1.9.18.2.1.4.1.1.1";
        }

        leaf qosUnmatchedPolicyRole {
          type CISCO-QOS-PIB-MIB:RoleCombination;
          description
           "Role combination for which this instance applies.";
          smiv2:max-access "read-only";
          smiv2:oid "1.3.6.1.4.1.9.18.2.1.4.1.1.2";
        }

        leaf qosUnmatchedPolicyDirection {
          type enumeration {
            enum "in" {
              value "0";
            }
            enum "out" {
              value "1";
            }
          }
          description
           "The direction of packet flow at the interface in question to
            which this instance applies.";
          smiv2:max-access "read-only";
          smiv2:oid "1.3.6.1.4.1.9.18.2.1.4.1.1.3";
        }

        leaf qosUnmatchedPolicyDscp {
          type CISCO-QOS-PIB-MIB:Dscp;
          description
           "The DSCP to classify the unmatched packet with.  This must be
            specified even if qosUnmatchedPolicyDscpTrusted is true.";
          smiv2:max-access "read-only";
          smiv2:oid "1.3.6.1.4.1.9.18.2.1.4.1.1.4";
        }

        leaf qosUnmatchedPolicyDscpTrusted {
          type boolean;
          description
           "If this attribute is true, then the Dscp associated with the
            packet is trusted, i.e., it is assumed to have already been
            set.  In this case, the Dscp is not rewritten with
            qosUnmatchedPolicyDscp (qosUnmatchedPolicyDscp is ignored)
            unless this is a non-IP packet and arrives untagged.  The
            packet is still policed as part of its micro flow and its
            aggregate flow.
            
            When a trusted action is applied to an input interface, the
            Dscp (for an IP packet) or CoS (for a non-IP packet)
            associated with the packet is the one contained in the packet.
            When a trusted action is applied to an output interface, the
            Dscp associated with the packet is the one that is the result
            of the input classification and policing.";
          smiv2:max-access "read-only";
          smiv2:oid "1.3.6.1.4.1.9.18.2.1.4.1.1.5";
        }

        leaf qosUnmatchPolMicroFlowPolicerId {
          type CISCO-QOS-PIB-MIB:PolicyInstanceId;
          description
           "An index identifying the instance of policer to apply to
            unmatched packets.  It must correspond to the integer index of
            an instance of class qosPolicerTable or be zero.  If zero, the
            microflow is not policed.";
          smiv2:max-access "read-only";
          smiv2:oid "1.3.6.1.4.1.9.18.2.1.4.1.1.6";
        }

        leaf qosUnmatchedPolicyAggregateId {
          type CISCO-QOS-PIB-MIB:PolicyInstanceId;
          description
           "An index identifying the aggregate that the packet belongs
            to.  It must correspond to the integer index of an instance of
            class qosAggregateTable or be zero.  If zero, the microflow
            does not belong to any aggregate and is not policed as part of
            any aggregate.";
          smiv2:max-access "read-only";
          smiv2:oid "1.3.6.1.4.1.9.18.2.1.4.1.1.7";
        }
      }
    }

    container qosPolicerTable {
      description
       "A class specifying policing parameters for both microflows
        and aggregate flows.  This table is designed for policing
        according to a token bucket scheme where an average rate and
        burst size is specified.";
      smiv2:oid "1.3.6.1.4.1.9.18.2.1.5.1";

      list qosPolicerEntry {
        key "qosPolicerId";
        description
         "An instance of this class specifies a set of policing
          parameters.";
        smiv2:oid "1.3.6.1.4.1.9.18.2.1.5.1.1";

        leaf qosPolicerId {
          type CISCO-QOS-PIB-MIB:PolicyInstanceId;
          description
           "An integer index to identify the instance of the policy class.";
          smiv2:max-access "not-accessible";
          smiv2:oid "1.3.6.1.4.1.9.18.2.1.5.1.1.1";
        }

        leaf qosPolicerRate {
          type uint32;
          description
           "The token rate.  It is specified in units of bit/s. A rate of
            zero means that all packets will be out of profile.  If the
            qosPolicerAction is set to drop then this effectively
            denies any service to packets policed by this policer.";
          smiv2:max-access "read-only";
          smiv2:oid "1.3.6.1.4.1.9.18.2.1.5.1.1.2";
        }

        leaf qosPolicerNormalBurst {
          type uint32;
          description
           "The normal size of a burst in terms of bits.";
          smiv2:max-access "read-only";
          smiv2:oid "1.3.6.1.4.1.9.18.2.1.5.1.1.3";
        }

        leaf qosPolicerExcessBurst {
          type uint32;
          description
           "The excess size of a burst in terms of bits.";
          smiv2:max-access "read-only";
          smiv2:oid "1.3.6.1.4.1.9.18.2.1.5.1.1.4";
        }

        leaf qosPolicerAction {
          type enumeration {
            enum "drop" {
              value "0";
            }
            enum "mark" {
              value "1";
            }
            enum "shape" {
              value "2";
            }
          }
          description
           "An indication of how to handle out of profile packets.  When
            the shape action is chosen then traffic is shaped to the rate
            specified by qosPolicerRate.";
          smiv2:max-access "read-only";
          smiv2:oid "1.3.6.1.4.1.9.18.2.1.5.1.1.5";
        }
      }
    }

    container qosAggregateTable {
      description
       "Instances of this class identify aggregate flows and the
        policer to apply to each.";
      smiv2:oid "1.3.6.1.4.1.9.18.2.1.5.2";

      list qosAggregateEntry {
        key "qosAggregateId";
        description
         "An instance of this class specifies the policer to apply to
          an aggregate flow.";
        smiv2:oid "1.3.6.1.4.1.9.18.2.1.5.2.1";

        leaf qosAggregateId {
          type CISCO-QOS-PIB-MIB:PolicyInstanceId;
          description
           "An integer index to identify the instance of the policy class.";
          smiv2:max-access "not-accessible";
          smiv2:oid "1.3.6.1.4.1.9.18.2.1.5.2.1.1";
        }

        leaf qosAggregatePolicerId {
          type CISCO-QOS-PIB-MIB:PolicyInstanceId;
          description
           "An index identifying the instance of policer to apply to the
            aggregate.  It must correspond to the integer index of an
            instance of class qosPolicerTable.";
          smiv2:max-access "read-only";
          smiv2:oid "1.3.6.1.4.1.9.18.2.1.5.2.1.2";
        }
      }
    }

    container qosMacClassificationTable {
      description
       "A class of MAC/Vlan tuples and their associated CoS values.";
      smiv2:oid "1.3.6.1.4.1.9.18.2.1.6.1";

      list qosMacClassificationEntry {
        key "qosMacClassificationId";
        description
         "An instance of this class specifies the mapping of a VLAN
          and a MAC address to a CoS value.";
        smiv2:oid "1.3.6.1.4.1.9.18.2.1.6.1.1";

        leaf qosMacClassificationId {
          type CISCO-QOS-PIB-MIB:PolicyInstanceId;
          description
           "An integer index to identify the instance of the policy class.";
          smiv2:max-access "not-accessible";
          smiv2:oid "1.3.6.1.4.1.9.18.2.1.6.1.1.1";
        }

        leaf qosDstMacVlan {
          type int32 {
            range "1..4095";
          }
          description
           "The VLAN of the destination MAC address of the L2 frame.";
          smiv2:max-access "read-only";
          smiv2:oid "1.3.6.1.4.1.9.18.2.1.6.1.1.2";
        }

        leaf qosDstMacAddress {
          type yang:mac-address;
          description
           "The destination MAC address of the L2 frame.";
          smiv2:max-access "read-only";
          smiv2:oid "1.3.6.1.4.1.9.18.2.1.6.1.1.3";
        }

        leaf qosDstMacCos {
          type CISCO-QOS-PIB-MIB:QosLayer2Cos;
          description
           "The CoS to assign the packet with the associated MAC/VLAN
            tuple.  Note that this CoS is overridden by the policies to
            classify the frame at layer 3 if there are any.";
          smiv2:max-access "read-only";
          smiv2:oid "1.3.6.1.4.1.9.18.2.1.6.1.1.4";
        }
      }
    }

    container qosIpAceTable {
      description
       "ACE definitions.";
      smiv2:oid "1.3.6.1.4.1.9.18.2.1.7.1";

      list qosIpAceEntry {
        key "qosIpAceId";
        description
         "An instance of this class specifies an ACE.";
        smiv2:oid "1.3.6.1.4.1.9.18.2.1.7.1.1";

        leaf qosIpAceId {
          type CISCO-QOS-PIB-MIB:PolicyInstanceId;
          description
           "An integer index to identify the instance of the policy class.";
          smiv2:max-access "not-accessible";
          smiv2:oid "1.3.6.1.4.1.9.18.2.1.7.1.1.1";
        }

        leaf qosIpAceDstAddr {
          type inet:ipv4-address;
          description
           "The IP address to match against the packet's destination IP
            address.";
          smiv2:max-access "read-only";
          smiv2:oid "1.3.6.1.4.1.9.18.2.1.7.1.1.2";
        }

        leaf qosIpAceDstAddrMask {
          type inet:ipv4-address;
          description
           "A mask for the matching of the destination IP address.";
          smiv2:max-access "read-only";
          smiv2:oid "1.3.6.1.4.1.9.18.2.1.7.1.1.3";
        }

        leaf qosIpAceSrcAddr {
          type inet:ipv4-address;
          description
           "The IP address to match against the packet's source IP
            address.";
          smiv2:max-access "read-only";
          smiv2:oid "1.3.6.1.4.1.9.18.2.1.7.1.1.4";
        }

        leaf qosIpAceSrcAddrMask {
          type inet:ipv4-address;
          description
           "A mask for the matching of the source IP address.";
          smiv2:max-access "read-only";
          smiv2:oid "1.3.6.1.4.1.9.18.2.1.7.1.1.5";
        }

        leaf qosIpAceDscpMin {
          type CISCO-QOS-PIB-MIB:Dscp;
          description
           "The minimum value that the DSCP in the packet can have and
            match this ACE.";
          smiv2:max-access "read-only";
          smiv2:oid "1.3.6.1.4.1.9.18.2.1.7.1.1.6";
        }

        leaf qosIpAceDscpMax {
          type CISCO-QOS-PIB-MIB:Dscp;
          description
           "The maximum value that the DSCP in the packet can have and
            match this ACE.";
          smiv2:max-access "read-only";
          smiv2:oid "1.3.6.1.4.1.9.18.2.1.7.1.1.7";
        }

        leaf qosIpAceProtocol {
          type int32 {
            range "0..255";
          }
          description
           "The IP protocol to match against the packet's protocol.
            A value of zero means match all.";
          smiv2:max-access "read-only";
          smiv2:oid "1.3.6.1.4.1.9.18.2.1.7.1.1.8";
        }

        leaf qosIpAceDstL4PortMin {
          type int32 {
            range "0..65535";
          }
          description
           "The minimum value that the packet's layer 4 dest port number
            can have and match this ACE.";
          smiv2:max-access "read-only";
          smiv2:oid "1.3.6.1.4.1.9.18.2.1.7.1.1.9";
        }

        leaf qosIpAceDstL4PortMax {
          type int32 {
            range "0..65535";
          }
          description
           "The maximum value that the packet's layer 4 dest port number
            can have and match this ACE.";
          smiv2:max-access "read-only";
          smiv2:oid "1.3.6.1.4.1.9.18.2.1.7.1.1.10";
        }

        leaf qosIpAceSrcL4PortMin {
          type int32 {
            range "0..65535";
          }
          description
           "The minimum value that the packet's layer 4 source port
            number can have and match this ACE.";
          smiv2:max-access "read-only";
          smiv2:oid "1.3.6.1.4.1.9.18.2.1.7.1.1.11";
        }

        leaf qosIpAceSrcL4PortMax {
          type int32 {
            range "0..65535";
          }
          description
           "The maximum value that the packet's layer 4 source port
            number can have and match this ACE.";
          smiv2:max-access "read-only";
          smiv2:oid "1.3.6.1.4.1.9.18.2.1.7.1.1.12";
        }

        leaf qosIpAcePermit {
          type boolean;
          description
           "If the packet matches this ACE and the value of this attribute
            is true, then the matching process terminates and the QoS
            associated with this ACE (indirectly through the ACL) is
            applied to the packet.  If the value of this attribute is false,
            then no more ACEs in this ACL are compared to this packet and
            matching continues with the first ACE of the next ACL.";
          smiv2:max-access "read-only";
          smiv2:oid "1.3.6.1.4.1.9.18.2.1.7.1.1.13";
        }
      }
    }

    container qosIpAclDefinitionTable {
      description
       "A class that defines a set of ACLs each being an ordered list
        of ACEs.";
      smiv2:oid "1.3.6.1.4.1.9.18.2.1.7.2";

      list qosIpAclDefinitionEntry {
        key "qosIpAclDefinitionId";
        description
         "An instance of this class specifies an ACE in an ACL and its
          order with respect to other ACEs in the same ACL.";
        smiv2:oid "1.3.6.1.4.1.9.18.2.1.7.2.1";

        leaf qosIpAclDefinitionId {
          type CISCO-QOS-PIB-MIB:PolicyInstanceId;
          description
           "An integer index to identify the instance of the policy class.";
          smiv2:max-access "not-accessible";
          smiv2:oid "1.3.6.1.4.1.9.18.2.1.7.2.1.1";
        }

        leaf qosIpAclId {
          type CISCO-QOS-PIB-MIB:PolicyInstanceId;
          description
           "An index for this ACL.  There will be one instance of
            policy class qosIpAclDefinition with this integer index for
            each ACE in the ACL per role combination.";
          smiv2:max-access "read-only";
          smiv2:oid "1.3.6.1.4.1.9.18.2.1.7.2.1.2";
        }

        leaf qosIpAceOrder {
          type uint32;
          description
           "An integer that determines the position of this ACE in the ACL.
            An ACE with a given order is positioned in the access contol
            list before one with a higher order.";
          smiv2:max-access "read-only";
          smiv2:oid "1.3.6.1.4.1.9.18.2.1.7.2.1.3";
        }

        leaf qosIpAclDefAceId {
          type CISCO-QOS-PIB-MIB:PolicyInstanceId;
          description
           "This attribute specifies the ACE in the qosIpAceTable that is
            in the ACL specified by qosIpAclId at the position specified
            by qosIpAceOrder.";
          smiv2:max-access "read-only";
          smiv2:oid "1.3.6.1.4.1.9.18.2.1.7.2.1.4";
        }
      }
    }

    container qosIpAclActionTable {
      description
       "A class that applies a set of ACLs to interfaces specifying,
        for each interface the order of the ACL with respect to other
        ACLs applied to the same interface and, for each ACL the
        action to take for a packet that matches a permit ACE in that
        ACL.  Interfaces are specified abstractly in terms of
        interface role combinations.";
      smiv2:oid "1.3.6.1.4.1.9.18.2.1.7.3";

      list qosIpAclActionEntry {
        key "qosIpAclActionId";
        description
         "An instance of this class applies an ACL to traffic in a
          particular direction on an interface with a particular role
          combination, and specifies the action for packets which match
          the ACL.";
        smiv2:oid "1.3.6.1.4.1.9.18.2.1.7.3.1";

        leaf qosIpAclActionId {
          type CISCO-QOS-PIB-MIB:PolicyInstanceId;
          description
           "An integer index to identify the instance of the policy class.";
          smiv2:max-access "not-accessible";
          smiv2:oid "1.3.6.1.4.1.9.18.2.1.7.3.1.1";
        }

        leaf qosIpAclActAclId {
          type CISCO-QOS-PIB-MIB:PolicyInstanceId;
          description
           "The ACL associated with this action.";
          smiv2:max-access "read-only";
          smiv2:oid "1.3.6.1.4.1.9.18.2.1.7.3.1.2";
        }

        leaf qosIpAclInterfaceRoles {
          type CISCO-QOS-PIB-MIB:RoleCombination;
          description
           "The interfaces to which this ACL applies specified in terms
            of a set of roles.";
          smiv2:max-access "read-only";
          smiv2:oid "1.3.6.1.4.1.9.18.2.1.7.3.1.3";
        }

        leaf qosIpAclInterfaceDirection {
          type enumeration {
            enum "in" {
              value "0";
            }
            enum "out" {
              value "1";
            }
          }
          description
           "The direction of packet flow at the interface in question to
            which this ACL applies.";
          smiv2:max-access "read-only";
          smiv2:oid "1.3.6.1.4.1.9.18.2.1.7.3.1.4";
        }

        leaf qosIpAclOrder {
          type uint32;
          description
           "An integer that determines the order of this ACL in the list
            of ACLs applied to interfaces of the specified role
            combination. An ACL with a given order is positioned in the
            list before one with a higher order.";
          smiv2:max-access "read-only";
          smiv2:oid "1.3.6.1.4.1.9.18.2.1.7.3.1.5";
        }

        leaf qosIpAclDscp {
          type CISCO-QOS-PIB-MIB:Dscp;
          description
           "The DSCP to classify the packet with in the event that the
            packet matches an ACE in this ACL and the ACE is a permit.";
          smiv2:max-access "read-only";
          smiv2:oid "1.3.6.1.4.1.9.18.2.1.7.3.1.6";
        }

        leaf qosIpAclDscpTrusted {
          type boolean;
          description
           "If this attribute is true, then the Dscp associated with
            the packet is trusted, i.e., it is assumed to have already
            been set.  In this case, the Dscp is not rewritten with
            qosIpAclDscp (qosIpAclDscp is ignored).  The packet is still
            policed as part of its micro flow and its aggregate flow.
            
            When a trusted action is applied to an input interface, the
            Dscp associated with the packet is the one contained in the
            packet.  When a trusted action is applied to an output
            interface, the Dscp associated with the packet is the one that
            is the result of the input classification and policing.";
          smiv2:max-access "read-only";
          smiv2:oid "1.3.6.1.4.1.9.18.2.1.7.3.1.7";
        }

        leaf qosIpAclMicroFlowPolicerId {
          type CISCO-QOS-PIB-MIB:PolicyInstanceId;
          description
           "An index identifying the instance of policer to apply to the
            microflow.  It must correspond to the integer index of an
            instance of class qosPolicerTableor be zero.  If zero, the
            microflow is not policed.";
          smiv2:max-access "read-only";
          smiv2:oid "1.3.6.1.4.1.9.18.2.1.7.3.1.8";
        }

        leaf qosIpAclAggregateId {
          type CISCO-QOS-PIB-MIB:PolicyInstanceId;
          description
           "An index identifying the aggregate that the packet belongs
            to.  It must correspond to the integer index of an instance of
            class qosAggregateTable or be zero.  If zero, the microflow
            does not belong to any aggregate and is not policed as part of
            any aggregate.";
          smiv2:max-access "read-only";
          smiv2:oid "1.3.6.1.4.1.9.18.2.1.7.3.1.9";
        }
      }
    }

    container qosIfSchedulingPreferencesTable {
      description
       "This class specifies the scheduling preference an interface
        chooses if it supports multiple scheduling types.  Higher
        values are preferred over lower values.";
      smiv2:oid "1.3.6.1.4.1.9.18.2.1.8.1";

      list qosIfSchedulingPreferenceEntry {
        key "qosIfSchedulingPreferenceId";
        description
         "An instance of this class specifies a scheduling preference
          for a queue-type on an interface with a particular role
          combination.";
        smiv2:oid "1.3.6.1.4.1.9.18.2.1.8.1.1";

        leaf qosIfSchedulingPreferenceId {
          type CISCO-QOS-PIB-MIB:PolicyInstanceId;
          description
           "An integer index to identify the instance of the policy class.";
          smiv2:max-access "not-accessible";
          smiv2:oid "1.3.6.1.4.1.9.18.2.1.8.1.1.1";
        }

        leaf qosIfSchedulingRoles {
          type CISCO-QOS-PIB-MIB:RoleCombination;
          description
           "The combination of roles the interface must have for this
            policy instance to apply to that interface.";
          smiv2:max-access "read-only";
          smiv2:oid "1.3.6.1.4.1.9.18.2.1.8.1.1.2";
        }

        leaf qosIfSchedulingPreference {
          type int32 {
            range "1..16";
          }
          description
           "The preference to use this scheduling discipline and queue
            type.  A higher value means a higher preference.  If two
            disciplines have the same preference the choice is a local
            decision.";
          smiv2:max-access "read-only";
          smiv2:oid "1.3.6.1.4.1.9.18.2.1.8.1.1.3";
        }

        leaf qosIfSchedulingDiscipline {
          type enumeration {
            enum "weightedFairQueueing" {
              value "1";
            }
            enum "weightedRoundRobin" {
              value "2";
            }
            enum "customQueueing" {
              value "3";
            }
            enum "priorityQueueing" {
              value "4";
            }
            enum "classBasedWFQ" {
              value "5";
            }
            enum "fifo" {
              value "6";
            }
            enum "pqWrr" {
              value "7";
            }
            enum "pqCbwfq" {
              value "8";
            }
          }
          description
           "An enumerate type for all the known scheduling disciplines.";
          smiv2:max-access "read-only";
          smiv2:oid "1.3.6.1.4.1.9.18.2.1.8.1.1.4";
        }

        leaf qosIfSchedulingQueueType {
          type CISCO-QOS-PIB-MIB:QosInterfaceQueueType;
          description
           "The queue type of this preference.";
          smiv2:max-access "read-only";
          smiv2:oid "1.3.6.1.4.1.9.18.2.1.8.1.1.5";
        }
      }
    }

    container qosIfDropPreferenceTable {
      description
       "This class specifies the preference of the drop mechanism an
        interface chooses if it supports multiple drop mechanisms.
        Higher values are preferred over lower values.";
      smiv2:oid "1.3.6.1.4.1.9.18.2.1.8.2";

      list qosIfDropPreferenceEntry {
        key "qosIfDropPreferenceId";
        description
         "An instance of this class specifies a drop preference for
          a drop mechanism on an interface with a particular role
          combination.";
        smiv2:oid "1.3.6.1.4.1.9.18.2.1.8.2.1";

        leaf qosIfDropPreferenceId {
          type CISCO-QOS-PIB-MIB:PolicyInstanceId;
          description
           "An integer index to identify the instance of the policy class.";
          smiv2:max-access "not-accessible";
          smiv2:oid "1.3.6.1.4.1.9.18.2.1.8.2.1.1";
        }

        leaf qosIfDropRoles {
          type CISCO-QOS-PIB-MIB:RoleCombination;
          description
           "The combination of roles the interface must have for this
            policy instance to apply to that interface.";
          smiv2:max-access "read-only";
          smiv2:oid "1.3.6.1.4.1.9.18.2.1.8.2.1.2";
        }

        leaf qosIfDropPreference {
          type int32 {
            range "1..16";
          }
          description
           "The preference to use this drop mechanism.  A higher value
            means a higher preference.  If two mechanisms have the same
            preference the choice is a local decision.";
          smiv2:max-access "read-only";
          smiv2:oid "1.3.6.1.4.1.9.18.2.1.8.2.1.3";
        }

        leaf qosIfDropDiscipline {
          type enumeration {
            enum "qosIfDropWRED" {
              value "1";
            }
            enum "qosIfDropTailDrop" {
              value "2";
            }
          }
          description
           "An enumerate type for all the known drop mechanisms.";
          smiv2:max-access "read-only";
          smiv2:oid "1.3.6.1.4.1.9.18.2.1.8.2.1.4";
        }
      }
    }

    container qosIfDscpAssignmentTable {
      description
       "The assignment of each DSCP to a queue and threshold for each
        interface queue type.";
      smiv2:oid "1.3.6.1.4.1.9.18.2.1.8.3";

      list qosIfDscpAssignmentEntry {
        key "qosIfDscpAssignmentId";
        description
         "An instance of this class specifies the queue and threshold
          set for a packet with a particular DSCP on an interface of
          a particular type with a particular role combination.";
        smiv2:oid "1.3.6.1.4.1.9.18.2.1.8.3.1";

        leaf qosIfDscpAssignmentId {
          type CISCO-QOS-PIB-MIB:PolicyInstanceId;
          description
           "An integer index to identify the instance of the policy class.";
          smiv2:max-access "not-accessible";
          smiv2:oid "1.3.6.1.4.1.9.18.2.1.8.3.1.1";
        }

        leaf qosIfDscpRoles {
          type CISCO-QOS-PIB-MIB:RoleCombination;
          description
           "The role combination the interface must be configured with.";
          smiv2:max-access "read-only";
          smiv2:oid "1.3.6.1.4.1.9.18.2.1.8.3.1.2";
        }

        leaf qosIfQueueType {
          type CISCO-QOS-PIB-MIB:QosInterfaceQueueType;
          description
           "The interface queue type to which this row applies.";
          smiv2:max-access "read-only";
          smiv2:oid "1.3.6.1.4.1.9.18.2.1.8.3.1.3";
        }

        leaf qosIfDscp {
          type CISCO-QOS-PIB-MIB:Dscp;
          description
           "The DSCP to which this row applies.";
          smiv2:max-access "read-only";
          smiv2:oid "1.3.6.1.4.1.9.18.2.1.8.3.1.4";
        }

        leaf qosIfQueue {
          type int32 {
            range "1..64";
          }
          description
           "The queue to which the DSCP applies for the given interface
            type.";
          smiv2:max-access "read-only";
          smiv2:oid "1.3.6.1.4.1.9.18.2.1.8.3.1.5";
        }

        leaf qosIfThresholdSet {
          type int32 {
            range "1..8";
          }
          description
           "The threshold set of the specified queue to which the DSCP
            applies for the given interface type.";
          smiv2:max-access "read-only";
          smiv2:oid "1.3.6.1.4.1.9.18.2.1.8.3.1.6";
        }
      }
    }

    container qosIfRedTable {
      description
       "A class of lower and upper values for each threshold set in a
        queue supporting WRED.  If the size of the queue for a given
        threshold is below the lower value then packets assigned to
        that threshold are always accepted into the queue.  If the
        size of the queue is above upper value then packets are always
        dropped.  If the size of the queue is between the lower and
        the upper then packets are randomly dropped.";
      smiv2:oid "1.3.6.1.4.1.9.18.2.1.8.4";

      list qosIfRedEntry {
        key "qosIfRedId";
        description
         "An instance of this class specifies threshold limits for a
          particular RED threshold of a given threshold set on an
          interface and with a particular role combination.";
        smiv2:oid "1.3.6.1.4.1.9.18.2.1.8.4.1";

        leaf qosIfRedId {
          type CISCO-QOS-PIB-MIB:PolicyInstanceId;
          description
           "An integer index to identify the instance of the policy class.";
          smiv2:max-access "not-accessible";
          smiv2:oid "1.3.6.1.4.1.9.18.2.1.8.4.1.1";
        }

        leaf qosIfRedRoles {
          type CISCO-QOS-PIB-MIB:RoleCombination;
          description
           "The role combination the interface must be configured with.";
          smiv2:max-access "read-only";
          smiv2:oid "1.3.6.1.4.1.9.18.2.1.8.4.1.2";
        }

        leaf qosIfRedNumThresholdSets {
          type CISCO-QOS-PIB-MIB:ThresholdSetRange;
          description
           "The values in this entry apply only to queues with the number
            of thresholds specified by this attribute.";
          smiv2:max-access "read-only";
          smiv2:oid "1.3.6.1.4.1.9.18.2.1.8.4.1.3";
        }

        leaf qosIfRedThresholdSet {
          type int32 {
            range "1..8";
          }
          description
           "The threshold set to which the lower and upper values apply.
            It must be in the range 1 through qosIfRedNumThresholdSets.
            There must be exactly one PRI for each value in this range.";
          smiv2:max-access "read-only";
          smiv2:oid "1.3.6.1.4.1.9.18.2.1.8.4.1.4";
        }

        leaf qosIfRedThresholdSetLower {
          type CISCO-QOS-PIB-MIB:Percent;
          description
           "The threshold value below which no packets are dropped.";
          smiv2:max-access "read-only";
          smiv2:oid "1.3.6.1.4.1.9.18.2.1.8.4.1.5";
        }

        leaf qosIfRedThresholdSetUpper {
          type CISCO-QOS-PIB-MIB:Percent;
          description
           "The threshold value above which all packets are dropped.";
          smiv2:max-access "read-only";
          smiv2:oid "1.3.6.1.4.1.9.18.2.1.8.4.1.6";
        }
      }
    }

    container qosIfTailDropTable {
      description
       "A class for threshold sets in a queue supporting tail drop.
        If the size of the queue for a given threshold set is at or
        below the specified value then packets assigned to that
        threshold set are always accepted into the queue.  If the size
        of the queue is above the specified value then packets are
        always dropped.";
      smiv2:oid "1.3.6.1.4.1.9.18.2.1.8.5";

      list qosIfTailDropEntry {
        key "qosIfTailDropId";
        description
         "An instance of this class specifies the queue depth for a
          particular tail-drop threshold set on an interface with a
          particular role combination.";
        smiv2:oid "1.3.6.1.4.1.9.18.2.1.8.5.1";

        leaf qosIfTailDropId {
          type CISCO-QOS-PIB-MIB:PolicyInstanceId;
          description
           "An integer index to identify the instance of the policy class.";
          smiv2:max-access "not-accessible";
          smiv2:oid "1.3.6.1.4.1.9.18.2.1.8.5.1.1";
        }

        leaf qosIfTailDropRoles {
          type CISCO-QOS-PIB-MIB:RoleCombination;
          description
           "The role combination the interface must be configured with.";
          smiv2:max-access "read-only";
          smiv2:oid "1.3.6.1.4.1.9.18.2.1.8.5.1.2";
        }

        leaf qosIfTailDropNumThresholdSets {
          type CISCO-QOS-PIB-MIB:ThresholdSetRange;
          description
           "The value in this entry applies only to queues with the
            number of thresholds specified by this attribute.";
          smiv2:max-access "read-only";
          smiv2:oid "1.3.6.1.4.1.9.18.2.1.8.5.1.3";
        }

        leaf qosIfTailDropThresholdSet {
          type int32 {
            range "1..8";
          }
          description
           "The threshold set to which the threshold value applies";
          smiv2:max-access "read-only";
          smiv2:oid "1.3.6.1.4.1.9.18.2.1.8.5.1.4";
        }

        leaf qosIfTailDropThresholdSetValue {
          type CISCO-QOS-PIB-MIB:Percent;
          description
           "The threshold value above which packets are dropped.";
          smiv2:max-access "read-only";
          smiv2:oid "1.3.6.1.4.1.9.18.2.1.8.5.1.5";
        }
      }
    }

    container qosIfWeightsTable {
      description
       "A class of scheduling weights for each queue of an interface
        that supports weighted round robin scheduling or a mix of
        priority queueing and weighted round robin.  For a queue with
        N priority queues, the N highest queue numbers are the
        priority queues with the highest queue number having the
        highest priority.  WRR is applied to the non-priority queues.";
      smiv2:oid "1.3.6.1.4.1.9.18.2.1.8.6";

      list qosIfWeightsEntry {
        key "qosIfWeightsId";
        description
         "An instance of this class specifies the scheduling weight for
          a particular queue of an interface with a particular number
          of queues and with a particular role combination.";
        smiv2:oid "1.3.6.1.4.1.9.18.2.1.8.6.1";

        leaf qosIfWeightsId {
          type CISCO-QOS-PIB-MIB:PolicyInstanceId;
          description
           "An integer index to identify the instance of the policy class.";
          smiv2:max-access "not-accessible";
          smiv2:oid "1.3.6.1.4.1.9.18.2.1.8.6.1.1";
        }

        leaf qosIfWeightsRoles {
          type CISCO-QOS-PIB-MIB:RoleCombination;
          description
           "The role combination the interface must be configured with.";
          smiv2:max-access "read-only";
          smiv2:oid "1.3.6.1.4.1.9.18.2.1.8.6.1.2";
        }

        leaf qosIfWeightsNumQueues {
          type CISCO-QOS-PIB-MIB:QueueRange;
          description
           "The value of the weight in this instance applies only to
            interfaces with the number of queues specified by this
            attribute.";
          smiv2:max-access "read-only";
          smiv2:oid "1.3.6.1.4.1.9.18.2.1.8.6.1.3";
        }

        leaf qosIfWeightsQueue {
          type int32 {
            range "1..64";
          }
          description
           "The queue to which the weight applies.";
          smiv2:max-access "read-only";
          smiv2:oid "1.3.6.1.4.1.9.18.2.1.8.6.1.4";
        }

        leaf qosIfWeightsDrainSize {
          type uint32;
          description
           "The maximum number of bytes that may be drained from the
            queue in one cycle.  The percentage of the bandwith allocated
            to this queue can be calculated from this attribute and the
            sum of the drain sizes of all the non-priority queues of the
            interface.";
          smiv2:max-access "read-only";
          smiv2:oid "1.3.6.1.4.1.9.18.2.1.8.6.1.5";
        }

        leaf qosIfWeightsQueueSize {
          type uint32;
          description
           "The size of the queue in bytes.  Some devices set queue size
            in terms of packets.  These devices must calculate the queue
            size in packets by assuming an average packet size suitable
            for the particular interface.
            
            Some devices have a fixed size buffer to be shared among all
            queues.  These devices must allocate a fraction of the
            total buffer space to this queue calculated as the the ratio
            of the queue size to the sum of the queue sizes for the
            interface.";
          smiv2:max-access "read-only";
          smiv2:oid "1.3.6.1.4.1.9.18.2.1.8.6.1.6";
        }
      }
    }
  }

  smiv2:alias "ciscoQosPIBMIB" {
    smiv2:oid "1.3.6.1.4.1.9.18.2.1";
  }

  smiv2:alias "qosPIBConformance" {
    smiv2:oid "1.3.6.1.4.1.9.18.2.1.1";
  }

  smiv2:alias "qosPIBCompliances" {
    smiv2:oid "1.3.6.1.4.1.9.18.2.1.1.1";
  }

  smiv2:alias "qosPIBGroups" {
    smiv2:oid "1.3.6.1.4.1.9.18.2.1.1.2";
  }

  smiv2:alias "qosDeviceConfig" {
    smiv2:oid "1.3.6.1.4.1.9.18.2.1.2";
  }

  smiv2:alias "qosDomainConfig" {
    smiv2:oid "1.3.6.1.4.1.9.18.2.1.3";
  }

  smiv2:alias "qosUnmatchedPolicy" {
    smiv2:oid "1.3.6.1.4.1.9.18.2.1.4";
  }

  smiv2:alias "qosPolicer" {
    smiv2:oid "1.3.6.1.4.1.9.18.2.1.5";
  }

  smiv2:alias "qosMacQos" {
    smiv2:oid "1.3.6.1.4.1.9.18.2.1.6";
  }

  smiv2:alias "qosIpQos" {
    smiv2:oid "1.3.6.1.4.1.9.18.2.1.7";
  }

  smiv2:alias "qosIfParameters" {
    smiv2:oid "1.3.6.1.4.1.9.18.2.1.8";
  }

}
