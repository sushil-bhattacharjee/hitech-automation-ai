/*
 * Generated by confdc --mib2yang-std
 * Source: mgmt/dmi/model/mib/src/CISCO-MEDIA-GATEWAY-MIB.mib
 */
/*
 * This YANG module has been generated by smidump 0.5.0:
 *
 *      smidump -f yang CISCO-MEDIA-GATEWAY-MIB
 *
 * Do not edit. Edit the source file instead!
 */

module CISCO-MEDIA-GATEWAY-MIB {

  namespace "urn:ietf:params:xml:ns:yang:smiv2:CISCO-MEDIA-GATEWAY-MIB";
  prefix CISCO-MEDIA-GATEWAY-MIB;

  import CISCO-TC {
    prefix "cisco-tc";
  }

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "        Cisco Systems
    Customer Service
    Postal: 170 W Tasman Drive
    San Jose, CA 95134
    USA
    Tel: +1 800 553-NETS
    E-mail: cs-voice-gateway@cisco.com";

  description
   "The MIB module for managing Trunk Media Gateway.  
    
    A Media Gateway is a network element that provides conversion 
    between the audio signals carried on telephone circuits and 
    data packets carried over the Internet or over other packet 
    data networks. 
    
    Trunk Media Gateway interface is between the telephone network 
    and a Voice over IP/ATM network. 
    The interface on a Trunk Gateway terminates a trunk connected 
    to PSTN switch (e.g., Class 5, Class 4, etc.).
    
    Media Gateways use a call control architecture where the call
    control 'intelligence' is outside the gateways and handled by
    external call control elements, called Media Gateway 
    Controllers (MGCs). 
    The MGCs or Call Agents, synchronize with each other to 
    send coherent commands to the gateways under their control.
    
    MGCs use master/slave protocols to command the gateways under 
    their control.  Examples of these protocols are:
      *  Simple Gateway Control Protocol
      *  Media Gateway Control Protocol
      *  Megaco (H.248)
      *  Simple Resource Control Protocol
    
    To connect MG to MGCs using these control protocols through 
    an IP/UDP Ports which must be configured. To resolve IP 
    Addresses, DNS name services may be used.";

  revision 2009-02-25 {
    description
     "Added object cmgwV23Enabled to
      cMediaGwTable.";
  }

  revision 2006-06-15 {
    description
     "Added object cmgwLawInterceptEnabled to
      cMediaGwTable.
      Added object cMediaGwCcCfgDefRtpNamePrefix to
      cMediaGwCallControlConfigTable.";
  }

  revision 2005-09-01 {
    description
     "Added object cmgwSrcFilterEnabled to
      cMediaGwTable.
      Added object cmgwSignalProtocolConfigVer
      to cmgwSignalProtocolTable.
      Added cMediaGwRscStatsTable.";
  }

  revision 2004-11-19 {
    description
     "Added object cmgwSignalProtocolPreference to
      cmgwSignalProtocolTable.";
  }

  revision 2004-07-30 {
    description
     "(1) Added the following objects: 
      cmgwVtMappingMode,
      cMediaGwCcCfgDefBearerTraffic,
      cmgwSignalMgcProtocolPort
      
      (2) Added new enum 'tgcp' to cmgwSignalProtocol ";
  }

  revision 2003-04-07 {
    description
     "Initial version of this MIB module";
  }

  typedef CGwServiceState {
    type enumeration {
      enum "inService" {
        value "1";
      }
      enum "forcedOutOfService" {
        value "2";
      }
      enum "gracefulOutOfService" {
        value "3";
      }
    }
    description
     "This textual convention defines the service state of media 
      gateway.
      The possible service states are:
      
        inService:
          Gateway is ready to provide service. 
          In this state, Gateway will respond to connection control
          requests, send autonomous messages to the call agent
          as applicable, etc.
      
        forcedOutOfService:
          Gateway is in Out-Of-Service State.
          All calls destroyed on the GW. 
          A Service Change message with FORCED method is sent to CA.
          No new connections are allowed.
      
        gracefulOutOfService:
          Gateway is in Out-Of-Service State.
          All existing calls will not be affected. 
          A Service Change message with GRACEFUL method is sent to CA.
          No new connections are allowed.";
  }

  typedef CGwAdminState {
    type enumeration {
      enum "inService" {
        value "1";
      }
      enum "forcedOutOfService" {
        value "2";
      }
      enum "gracefulOutOfService" {
        value "3";
      }
    }
    description
     "This textual convention defines the administrative state of  
      media gateway.
      
      The possible administrative states are as follows:
        inService: 
            Gateway would be restored to in-service status 
            and a ServiceChange with method RESTART message will be 
            sent to Call Agent
           
        forcefulOutOfService: 
            Gateway would be in Out-Of-Service State 
            Any existing connections on the GW will be deleted.
            A ServiceChange with method FORCED message will be 
            sent to call agent.
            New connections would be blocked.       
      
        gracefulOutOfService: 
            Gateway would be in in Out-Of-Service State 
            Any existing connections on the GW will not be affected.
            A ServiceChange with method GRACEFUL message will be 
            sent to call agent.
            New connections would be blocked.";
  }

  typedef GatewayLifNumber {
    type uint32 {
      range "1..255";
    }
    description
     "An index that uniquely identifies a LIF (Logical Interface)
      in the media gateway. 
      LIF is a logical interface which groups TDM(DS1) interfaces
      into packet resource partitions (PVCs) in the media gateway.  
      LIF is used for:
         AAL5 (VoIP) switching 
         AAL2 (VoATM) switching, only if support virtual gateway ";
  }

  typedef CVoiceTonePlanIndex {
    type uint32 {
      range "1..65535";
    }
    description
     "This textual convention defines the type of index for 
      identifying a voice tone plane in a Media gateway.";
  }

  typedef CVoiceTonePlanIndexOrZero {
    type uint32 {
      range "0..65535";
    }
    description
     "This textual convention uniquely identifies the voice tone plan 
      to be used in a voice DS0 group.
      
      The value of 0 means the default tone plan specified in
      the media gateway (the value of cMediaGwCcCfgDefaultTonePlanId)
      to be used.
      
      A value greater than 0 means the tone plan specified by the 
      index of the cvtcTonePlanTable to be used (same as 
      cvtcTonePlanId).";
  }

  typedef CCallControlProfileIndex {
    type uint32 {
      range "1..65535";
    }
    description
     "This textual convention defines the type of index that is 
      used for identifying a call control profile of XGCP and 
      H.248 protocol.";
  }

  typedef CCallControlProfileIndexOrZero {
    type uint32 {
      range "0..65535";
    }
    description
     "This textual convention is an extension of the 
      CCallControlProfileIndex convention. 
      The latter defines a greater than zero value used to identify 
      a call control profile in a media gateway.  
      This extension permits the additional value of zero.
      The value of '0' means the default call control profile of the 
      media gateway.";
  }

  typedef CCallControlJitterDelayMode {
    type enumeration {
      enum "adaptive" {
        value "1";
      }
      enum "fixed" {
        value "2";
      }
    }
    description
     "This textual convention defines the jitter buffer mode in
      a call connection.
      
      adaptive(1) - means to use jitter nominal delay as the 
                    initial jitter buffers size and let the DSP
                    pick the optimal value of the jitter buffer
                    size between the range of jitter maximum delay
                    and jitter minimum delay.
      
      fixed(2) - means to use a constant jitter buffer size
                 which is specified by jitter nominal delay.";
  }


  container CISCO-MEDIA-GATEWAY-MIB {
    config false;

    container cMediaGwTable {
      description
       "This table contains the global media gateway parameters
        information.
        It supports the modification of the global media gateway 
        parameters.";
      smiv2:oid "1.3.6.1.4.1.9.9.324.1.1.1";

      list cMediaGwEntry {
        key "cmgwIndex";
        description
         "A Media Gateway Entry.  
          At system power-up, an entry is created by the agent 
          if the system detects a media gateway module has been added 
          to the system, and an entry is deleted if the entry associated
          media gateway module has been removed from the system.";
        smiv2:oid "1.3.6.1.4.1.9.9.324.1.1.1.1";

        leaf cmgwIndex {
          type int32 {
            range "1..2147483647";
          }
          description
           "An index that uniquely identifies an entry in the 
            cMediaGwTable.";
          smiv2:max-access "not-accessible";
          smiv2:oid "1.3.6.1.4.1.9.9.324.1.1.1.1.1";
        }

        leaf cmgwDomainName {
          type snmp-framework:SnmpAdminString {
            length "0..64";
          }
          description
           "This object is used to represent a domain name under which   
            the Media Gateway could also be registered in a DNS name
            server. 
            
            The value of this object reflects the value of 
            cmgwConfigDomainName from the entry with a value of 
            'gateway(1)' for object cmgwConfigDomainNameEntity of 
            cMediaGwDomainNameConfigTable.
            
            If there is no entry in cMediaGwDomainNameConfigTable with
            'gateway(1)' of cmgwConfigDomainNameEntity, then
            the value of this object will be empty string.";
          smiv2:max-access "read-only";
          smiv2:oid "1.3.6.1.4.1.9.9.324.1.1.1.1.2";
        }

        leaf cmgwPhysicalIndex {
          type cisco-tc:EntPhysicalIndexOrZero;
          description
           "This object represents the entPhysicalIndex of the
            card in which media gateway is running. It will contain
            value 0 if the entPhysicalIndex value is not available or 
            not applicable";
          smiv2:max-access "read-only";
          smiv2:oid "1.3.6.1.4.1.9.9.324.1.1.1.1.3";
        }

        leaf cmgwServiceState {
          type CISCO-MEDIA-GATEWAY-MIB:CGwServiceState;
          description
           "This object indicates the current service state of the Media 
            Gateway.
            This object is controlled by 'cmgwAdminState' 
            object.";
          smiv2:max-access "read-only";
          smiv2:oid "1.3.6.1.4.1.9.9.324.1.1.1.1.4";
        }

        leaf cmgwAdminState {
          type CISCO-MEDIA-GATEWAY-MIB:CGwAdminState;
          description
           "This object is used to change the service state of 
            the Media Gateway from inService to outOfService or from 
            outOfService to inService. 
            The resulting service state of the gateway is represented  
            by 'cmgwServiceState'.";
          smiv2:max-access "read-write";
          smiv2:oid "1.3.6.1.4.1.9.9.324.1.1.1.1.5";
        }

        leaf cmgwGraceTime {
          type int32 {
            range "-1..65535";
          }
          units "seconds";
          description
           "This object is used to represent grace period.
            The grace period (restart delay in RSIP message) is  
            expressed in a number of seconds. 
            It means how soon the gateway will be taken out of service.
            The value -1 indicates that the grace period time is
            disabled.";
          smiv2:defval "-1";
          smiv2:max-access "read-write";
          smiv2:oid "1.3.6.1.4.1.9.9.324.1.1.1.1.6";
        }

        leaf cmgwVtMappingMode {
          type enumeration {
            enum "standard" {
              value "1";
            }
            enum "titan" {
              value "2";
            }
          }
          description
           "This object is used to represent the VT (sonet Virtual
            Tributary) counting.
            
            standard - standard counting (based on Bellcore TR253)
            titan    - TITAN5500 counting (based on Tellabs TITAN 5500)
            
            Note: 'titan' is valid only if sonet line medium type 
                  (sonetMediumType of SONET-MIB) is 'sonet' and 
                  sonet path payload type (cspSonetPathPayload of
                  CISCO-SONET-MIB) is 'vt15vc11'.";
          smiv2:max-access "read-write";
          smiv2:oid "1.3.6.1.4.1.9.9.324.1.1.1.1.7";
        }

        leaf cmgwSrcFilterEnabled {
          type boolean;
          description
           "This object is used to enable or disable the source IP
            and port filtering with MGC for security consideration
            as follows:
              'true'  - source IP and port filter is enabled 
              'false' - source IP and port filter is disable ";
          smiv2:defval "false";
          smiv2:max-access "read-write";
          smiv2:oid "1.3.6.1.4.1.9.9.324.1.1.1.1.8";
        }

        leaf cmgwLawInterceptEnabled {
          type boolean;
          description
           "This object is used to enable or disable the lawful
            intercept for government.
            as follows:
              'true'  - enable lawful intercept
              'false' - disable lawful intercept";
          smiv2:defval "false";
          smiv2:max-access "read-write";
          smiv2:oid "1.3.6.1.4.1.9.9.324.1.1.1.1.9";
        }

        leaf cmgwV23Enabled {
          type boolean;
          description
           "This object is to enable or disable V23 tone.
            Setting the object value to 'true', will cause VXSM (Voice Switching
            Service Module) to detect V23 tone.";
          smiv2:defval "false";
          smiv2:max-access "read-write";
          smiv2:oid "1.3.6.1.4.1.9.9.324.1.1.1.1.10";
        }
      }
    }

    container cmgwSignalProtocolTable {
      description
       "This table contains the available signaling protocols that
        are supported by the media gateway for communication with
        MGCs.";
      smiv2:oid "1.3.6.1.4.1.9.9.324.1.1.2";

      list cmgwSignalProtocolEntry {
        key "cmgwIndex cmgwSignalProtocolIndex";
        description
         "Each entry represents an signaling protocol supported
          by the media gateway.";
        smiv2:oid "1.3.6.1.4.1.9.9.324.1.1.2.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwSignalProtocolIndex {
          type int32 {
            range "1..65535";
          }
          description
           "An index that uniquely identifies an entry in
            cmgwSignalProtocolTable.";
          smiv2:max-access "not-accessible";
          smiv2:oid "1.3.6.1.4.1.9.9.324.1.1.2.1.1";
        }

        leaf cmgwSignalProtocol {
          type enumeration {
            enum "other" {
              value "1";
            }
            enum "mgcp" {
              value "2";
            }
            enum "h248" {
              value "3";
            }
            enum "tgcp" {
              value "4";
            }
          }
          description
           "This object is used to represent the protocol type.
            other - None of the following types.
            mgcp  - Media Gateway Control Protocol
            h248 - Media Gateway Control (ITU H.248)
            tgcp - Trunking Gateway Control Protocol";
          smiv2:max-access "read-only";
          smiv2:oid "1.3.6.1.4.1.9.9.324.1.1.2.1.2";
        }

        leaf cmgwSignalProtocolVersion {
          type snmp-framework:SnmpAdminString {
            length "1..16";
          }
          description
           "This object is used to represent the protocol version. 
            For example cmgwSignalProtocol is 'mgcp(2)' and
            this object is string '1.0'. cmgwSignalProtocol is 
            'h248(3)' and this object is set to '2.0'.";
          reference
           "MCGP 1.0 is documented in RFC2705.";
          smiv2:max-access "read-only";
          smiv2:oid "1.3.6.1.4.1.9.9.324.1.1.2.1.3";
        }

        leaf cmgwSignalProtocolPort {
          type cisco-tc:CiscoPort;
          description
           "This object is used to represent the UDP port associated 
            with the protocol.
            If the value of cmgwSignalProtocol is 'mgcp(2)' and the
            value of cmgwSignalProtcolVersion is '1.0', the default
            value of this object is '2727'. 
            If the value of cmgwSignalProtocol is 'h248(3)' and the
            value of cmgwSignalProtcolVersion is '1.0', the default
            value of this object is '2944'.";
          smiv2:max-access "read-write";
          smiv2:oid "1.3.6.1.4.1.9.9.324.1.1.2.1.4";
        }

        leaf cmgwSignalMgcProtocolPort {
          type inet:port-number;
          description
           "This object specifies the protocol port of the Media Gateway
            Controller (MGC).
            If the value of cmgwSignalProtocol is 'mgcp(2)' or 'tgcp(4)'
            and the value of cmgwSignalProtcolVersion is '1.0', the
            default value of this object is '2427'.
            If the value of cmgwSignalProtocol is 'h248(3)' and the
            value of cmgwSignalProtcolVersion is '1.0', the default
            value of this object is '2944'.";
          smiv2:max-access "read-write";
          smiv2:oid "1.3.6.1.4.1.9.9.324.1.1.2.1.5";
        }

        leaf cmgwSignalProtocolPreference {
          type int32 {
            range "0..255";
          }
          description
           "This object specifies the preference of the signal protocol 
            supported in the media gateway.
            
            If this object is set to 0, the corresponding signal
            protocol will not be used by the gateway.
             
            The value of this object is unique within the corresponding
            gateway. The entry with lower value has higher preference.";
          smiv2:max-access "read-write";
          smiv2:oid "1.3.6.1.4.1.9.9.324.1.1.2.1.6";
        }

        leaf cmgwSignalProtocolConfigVer {
          type snmp-framework:SnmpAdminString {
            length "1..16";
          }
          description
           "This object specifies the protocol version
            used by the gateway in the messages to MGC
            in order to exchange the service capabilities.
            
            For example cmgwSignalProtocol is 'h248(3)' and
            this object can be string '1' or '1.0', '2' or '2.0'. 
            
            'MAX' is a special string indicating the gateway will
            use the highest protocol version supported in the 
            gateway, but it can be changed to lower version after 
            it negotiates with MGC. The final negotiated protocol
            version will be indicated in cmgwSignalProtocolVersion.
            
            The version strings other than 'MAX' can be specified for
            the gateway to communicate with the MGC which doesn't
            support service capabilities negotiation. For example if
            a MGC supports only version 1.0 MGCP, this object should
            be set to '1' to instruct the gateway using MGCP 
            version 1.0 format messages to communicate with MGC. ";
          smiv2:max-access "read-write";
          smiv2:oid "1.3.6.1.4.1.9.9.324.1.1.2.1.7";
        }
      }
    }

    container cMediaGwIpConfigTable {
      description
       "This table contains a list of media gateway IP address and
        the IP address associated interface information.
        
        If IP address associated interface is PVC, only 
        aal5 control PVC or aal5 bearer PVC are valid.       
        When the PVC is aal5 control, the IP address is used to 
        communicate to MGC; when the PVC is aal5 bearer, the IP
        address is used to communicate to other gateway.
        The PVC information is kept in cwAtmChanExtConfigTable:
         cwacChanPvcType:      aal5/aal2/aal1
         cwacChanApplication:  control/bearer/signaling
        
        If IP address associated interface is not PVC, refer to the 
        IP addresses associated interface table for the usage
        of IP address.";
      smiv2:oid "1.3.6.1.4.1.9.9.324.1.1.3";

      list cMediaGwIpConfigEntry {
        key "cmgwIndex cmgwIpConfigIndex";
        description
         "A Media Gateway IP configuration entry. 
          Each entry represents a media gateway IP address for MGCs
          to communicate with the media gateway.";
        smiv2:oid "1.3.6.1.4.1.9.9.324.1.1.3.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwIpConfigIndex {
          type int32 {
            range "1..64";
          }
          description
           "A unique index to identify each media gateway IP address.";
          smiv2:max-access "not-accessible";
          smiv2:oid "1.3.6.1.4.1.9.9.324.1.1.3.1.1";
        }

        leaf cmgwIpConfigIfIndex {
          type if-mib:InterfaceIndexOrZero;
          description
           "This object is ifIndex of the interface which is associated
            to the media gateway IP address.
            
            For ATM interface, the IP address should be associated to
            an existing PVC:
               cmgwIpConfigIfIndex represents port of the PVC
               cmgwIpConfigVpi represents VPI of the PVC
               cmgwIpConfigVci represents VCI of the PVC
            And one PVC only can be associated with one IP address.
            
            If this object is set to zero which means the IP address
            is not associated to any interface.";
          smiv2:max-access "read-write";
          smiv2:oid "1.3.6.1.4.1.9.9.324.1.1.3.1.2";
        }

        leaf cmgwIpConfigVpi {
          type int32 {
            range "-1..4095";
          }
          description
           "This object represents VPI of the PVC which is associated
            to the IP address.
            If the IP address is not associated to PVC, the value 
            of this object is set to -1.";
          smiv2:max-access "read-write";
          smiv2:oid "1.3.6.1.4.1.9.9.324.1.1.3.1.3";
        }

        leaf cmgwIpConfigVci {
          type int32 {
            range "-1..65535";
          }
          description
           "This object represents VCI of the PVC which is associated
            to the IP address.
            If the IP address is not associated to PVC, the value
            of this object is set to -1.";
          smiv2:max-access "read-write";
          smiv2:oid "1.3.6.1.4.1.9.9.324.1.1.3.1.4";
        }

        leaf cmgwIpConfigAddrType {
          type inet-address:InetAddressType;
          description
           "This object is the IP address type.";
          smiv2:defval "ipv4";
          smiv2:max-access "read-write";
          smiv2:oid "1.3.6.1.4.1.9.9.324.1.1.3.1.5";
        }

        leaf cmgwIpConfigAddress {
          type inet-address:InetAddress;
          description
           "The configured IP address of media gateway.
            This object can not be modified.";
          smiv2:max-access "read-write";
          smiv2:oid "1.3.6.1.4.1.9.9.324.1.1.3.1.6";
        }

        leaf cmgwIpConfigSubnetMask {
          type inet-address:InetAddressPrefixLength;
          description
           "This object is used to specify the number of leading one   
            bits which from the mask to be logical-ANDed with the media  
            gateway address before being compared to the value in the 
            cmgwIpCofigAddress.
            
            Any assignment (implicit or otherwise) of an instance of
            this object to a value x must be rejected if the bitwise
            logical-AND of the mask formed from x with the value 
            of the corresponding instance of the cmgwIpCofigAddress 
            object is not equal to cmgwIpCofigAddress.";
          smiv2:max-access "read-write";
          smiv2:oid "1.3.6.1.4.1.9.9.324.1.1.3.1.7";
        }

        leaf cmgwIpConfigDefaultGwIp {
          type boolean;
          description
           "This object specifies cmgwIpConfigAddress of the entry
            will become the default gateway address.
            This object can be set to 'true' for only one entry in
            the table.";
          smiv2:defval "false";
          smiv2:max-access "read-write";
          smiv2:oid "1.3.6.1.4.1.9.9.324.1.1.3.1.8";
        }

        leaf cmgwIpConfigForRemoteMapping {
          type boolean;
          description
           "This object specifies whether the address defined in
            cmgwIpConfigAddress is the address mapping at the
            remote end of this PVC. 
            
            If this object is set to 'true', the address defined
            in cmgwIpConfigAddress is for the remote end of the PVC.
            If this object is set to 'false', the address defined
            in cmgwIpConfigAddress is for the local end of the PVC.";
          smiv2:defval "false";
          smiv2:max-access "read-write";
          smiv2:oid "1.3.6.1.4.1.9.9.324.1.1.3.1.9";
        }

        leaf cmgwIpConfigRowStatus {
          type snmpv2-tc:RowStatus;
          description
           "This object is used to add and delete an entry.
            
            When an entry of the table is created, the following 
            objects are mandatory:
                cmgwIpConfigIfIndex
                cmgwIpConfigVpi
                cmgwIpConfigVci
                cmgwIpConfigAddress
                cmgwIpConfigSubnetMask
            
            These objects can not be modified after the value of this
            object is set to 'active'. 
            Modification can only be done by deleting and re-adding the 
            entry again.
            
            After the system verify the validity of the data, it
            will set the cmgwIpConfigRowStatus to 'active'.";
          smiv2:max-access "read-write";
          smiv2:oid "1.3.6.1.4.1.9.9.324.1.1.3.1.10";
        }
      }
    }

    container cMediaGwDomainNameConfigTable {
      description
       "This table provides the domain names which are configured by 
        users. 
        The domain names can be used to represent IP addresses 
        for:
            gateway
            External DNS name server
            MGC (call agent) ";
      smiv2:oid "1.3.6.1.4.1.9.9.324.1.1.4";

      list cMediaGwDomainNameConfigEntry {
        key "cmgwIndex cmgwConfigDomainNameIndex";
        description
         "Each entry represents a domain name used in the system.
          
          Creation and deletion are supported. Modification
          is prohibited.";
        smiv2:oid "1.3.6.1.4.1.9.9.324.1.1.4.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwConfigDomainNameIndex {
          type int32 {
            range "1..128";
          }
          description
           "An index that is uniquely identifies a domain name
            configured in the system.";
          smiv2:max-access "not-accessible";
          smiv2:oid "1.3.6.1.4.1.9.9.324.1.1.4.1.1";
        }

        leaf cmgwConfigDomainNameEntity {
          type enumeration {
            enum "gateway" {
              value "1";
            }
            enum "dnsServer" {
              value "2";
            }
            enum "mgc" {
              value "3";
            }
          }
          description
           "This object indicates which entity to use this domain name.
            
            gateway(1)   - The domain name of media gateway.
                           With the same cmgwIndex, there is one and 
                           only one entry allowed with the value 
                           'gateway(1)' of this object.
            
            dnsServer(2) - The domain name of DNS name server that is used 
                           by Media gateway to find Internet Network 
                           Address from a DNS name.
            
            mgc(3)       - The domain name of a MGC (Media Gateway
                           Controller) associated with the media 
                           gateway. ";
          smiv2:max-access "read-write";
          smiv2:oid "1.3.6.1.4.1.9.9.324.1.1.4.1.2";
        }

        leaf cmgwConfigDomainName {
          type snmp-framework:SnmpAdminString {
            length "1..64";
          }
          description
           "This object specifies the domain name.
            
            The domain name should be unique if there are more than
            one entries having the same value in the object 
            cmgwConfigDomainNameEntity.
            For example, the gateway domain name should be unique 
            if the cmgwConfigDomainNameEntity has the value of 
            'gateway(1)'.";
          smiv2:max-access "read-write";
          smiv2:oid "1.3.6.1.4.1.9.9.324.1.1.4.1.3";
        }

        leaf cmgwConfigDomainNameRowStatus {
          type snmpv2-tc:RowStatus;
          description
           "This object is used to add and delete an entry.
            
            When an entry is created, the following objects
            are mandatory:
                 cmgwConfigDomainName
                 cmgwConfigDomainNameEntity
            
            When deleting domain name of DNS name server
            (cmgwConfigDomainNameEntity is dnsServer (2)), the 
            cMediaGwDnsIpConfigTable should be empty.
            
            Adding/deleting entry with cmgwConfigDomainNameEntity
            of 'mgc' will cause adding/deleting entry in 
            cMgcConfigTable (CISCO-MGC-MIB) automatically.
            
            The cmgwConfigDomainName and cmgwConfigDomainNameEntity
            can not be modified if the value of this object is
            'active'. ";
          smiv2:max-access "read-write";
          smiv2:oid "1.3.6.1.4.1.9.9.324.1.1.4.1.4";
        }
      }
    }

    container cMediaGwDnsIpConfigTable {
      description
       "There is only one DNS name server on a gateway
        and the domain name of the DNS name server is put on 
        cMediaGwDomainNameConfigTable with 'dnsServer (2)'.
        
        There could be multi IP addresses are associated with the
        DNS name server, this table is used to store these IP 
        addresses.
        
        If any domain name using external resolution, the last entry
        of this table is not allowed to be deleted.";
      smiv2:oid "1.3.6.1.4.1.9.9.324.1.1.5";

      list cMediaGwDnsIpConfigEntry {
        key "cmgwIndex cmgwDnsIpIndex";
        description
         "Each entry represents an IP address of the DNS name 
          server.";
        smiv2:oid "1.3.6.1.4.1.9.9.324.1.1.5.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwDnsIpIndex {
          type int32 {
            range "1..6";
          }
          description
           "An index that uniquely identifies an IP address of DNS
            name server.";
          smiv2:max-access "not-accessible";
          smiv2:oid "1.3.6.1.4.1.9.9.324.1.1.5.1.1";
        }

        leaf cmgwDnsDomainName {
          type snmp-framework:SnmpAdminString {
            length "1..64";
          }
          description
           "The domain name of DNS name server.
            
            The value of this object reflects the value of 
            cmgwConfigDomainName from the entry with a value of 
            'dnsServer(2)' for object cmgwConfigDomainNameEntity of 
            cMediaGwDomainNameConfigTable.
            
            If there is no entry in cMediaGwDomainNameConfigTable with
            'dnsServer(2)' of cmgwConfigDomainNameEntity, then
            the value of this object will be empty string.";
          smiv2:max-access "read-only";
          smiv2:oid "1.3.6.1.4.1.9.9.324.1.1.5.1.2";
        }

        leaf cmgwDnsIpType {
          type inet-address:InetAddressType;
          description
           "DNS name server IP address type.";
          smiv2:defval "ipv4";
          smiv2:max-access "read-write";
          smiv2:oid "1.3.6.1.4.1.9.9.324.1.1.5.1.3";
        }

        leaf cmgwDnsIp {
          type inet-address:InetAddress;
          description
           "The IP address of DNS name server.
            The IP address of DNS name server must be unique
            in this table.";
          smiv2:max-access "read-write";
          smiv2:oid "1.3.6.1.4.1.9.9.324.1.1.5.1.4";
        }

        leaf cmgwDnsIpRowStatus {
          type snmpv2-tc:RowStatus;
          description
           "This object is used to add and delete an entry.
            
            When an entry of the table is created, the value of
            this object should be set to 'createAndGo' and the
            following objects are mandatory:
                cmgwDnsIp
            
            When the user wants to delete the entry, the value of
            this object should be set to 'destroy'.
            
            The entry can not be modified if the value of this 
            object is 'active'.";
          smiv2:max-access "read-write";
          smiv2:oid "1.3.6.1.4.1.9.9.324.1.1.5.1.5";
        }
      }
    }

    container cmgwLifTable {
      description
       "This table is for managing LIF (Logical Interface) 
        in a media gateway. 
        
        LIF is a logical interface which groups the TDM 
        DSx1s associated with a set of packet resource partitions 
        (PVCs) in a media gateway.
        
        LIF is used for:
        1. VoIP switching 
        2. VoATM switching ";
      smiv2:oid "1.3.6.1.4.1.9.9.324.1.1.6";

      list cmgwLifEntry {
        key "cmgwIndex cmgwLifNumber";
        description
         "An entry of this table is created by the media gateway
          when it supports the VoIP/VoATM application.";
        smiv2:oid "1.3.6.1.4.1.9.9.324.1.1.6.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwLifNumber {
          type CISCO-MEDIA-GATEWAY-MIB:GatewayLifNumber;
          description
           "An index that uniquely identifies a LIF in the 
            media gateway.";
          smiv2:max-access "not-accessible";
          smiv2:oid "1.3.6.1.4.1.9.9.324.1.1.6.1.1";
        }

        leaf cmgwLifPvcCount {
          type yang:gauge32 {
            range "0..10000";
          }
          description
           "This object represents the total number of PVC within 
            this LIF.
            
            When users associate/disassociate a PVC with a LIF 
            by giving a non-zero/zero value of cwacChanLifNum
            in cwAtmChanExtConfigTable, the value of this object 
            will be incremented/decremented accordingly.
            
            The value zero means there is no PVC associated with 
            the LIF.";
          smiv2:max-access "read-only";
          smiv2:oid "1.3.6.1.4.1.9.9.324.1.1.6.1.2";
        }

        leaf cmgwLifVoiceIfCount {
          type yang:gauge32 {
            range "0..1000";
          }
          description
           "This object represents the total number of Voice Interfaces
            within this LIF.
            
            When users associate/disassociate a Voice Interface with
            a LIF by giving a non-zero/zero value of 
            ccasVoiceCfgLifNumber for the DS0 group in 
            ccasVoiceExtCfgTable, the value of this object will be 
            incremented/decremented accordingly. 
            
            The value zero means there is no Voice Interface associated
            with the LIF.";
          smiv2:max-access "read-only";
          smiv2:oid "1.3.6.1.4.1.9.9.324.1.1.6.1.3";
        }
      }
    }

    container cMediaGwCallControlConfigTable {
      description
       "This table defines general call control attributes for
        the media gateway.";
      smiv2:oid "1.3.6.1.4.1.9.9.324.1.1.7";

      list cMediaGwCallControlConfigEntry {
        key "cmgwIndex";
        description
         "One entry for each media gateway which supports call control 
          protocol.";
        smiv2:oid "1.3.6.1.4.1.9.9.324.1.1.7.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cMediaGwCcCfgControlTos {
          type uint32 {
            range "0..255";
          }
          description
           "This object specifies Type Of Service (TOS) field of
            IP header for the signaling control packet in VoIP
            application.";
          smiv2:defval "96";
          smiv2:max-access "read-write";
          smiv2:oid "1.3.6.1.4.1.9.9.324.1.1.7.1.1";
        }

        leaf cMediaGwCcCfgBearerTos {
          type uint32 {
            range "0..255";
          }
          description
           "This object specifies Type Of Service (TOS) field
            of IP header for the voice payload packet in VoIP
            application.";
          smiv2:defval "160";
          smiv2:max-access "read-write";
          smiv2:oid "1.3.6.1.4.1.9.9.324.1.1.7.1.2";
        }

        leaf cMediaGwCcCfgNtePayload {
          type uint32 {
            range "96..127";
          }
          description
           "This object specifies NTE (Named Telephony Events)
            payload type.";
          reference
           "RFC2833, 3. RTP Payload Format for Named Telephone Events";
          smiv2:defval "101";
          smiv2:max-access "read-write";
          smiv2:oid "1.3.6.1.4.1.9.9.324.1.1.7.1.3";
        }

        leaf cMediaGwCcCfgNsePayload {
          type uint32 {
            range "98..117";
          }
          description
           "This object specifies NSE (Network Signaling Events)
            payload type.";
          smiv2:defval "100";
          smiv2:max-access "read-write";
          smiv2:oid "1.3.6.1.4.1.9.9.324.1.1.7.1.4";
        }

        leaf cMediaGwCcCfgNseRespTimer {
          type uint32 {
            range "250..10000";
          }
          units "milliseconds";
          description
           "This object specifies Network Signaling Event (NSE)
            timeout value.";
          smiv2:defval "1000";
          smiv2:max-access "read-write";
          smiv2:oid "1.3.6.1.4.1.9.9.324.1.1.7.1.5";
        }

        leaf cMediaGwCcCfgVbdJitterDelayMode {
          type CISCO-MEDIA-GATEWAY-MIB:CCallControlJitterDelayMode;
          description
           "The object specifies the jitter buffer mode applied to
            a VBD (Voice Band Data) call connection.
            
            adaptive - means to use cMediaGwCcCfgVbdJitterNomDelay as
                       the initial jitter buffers size and let the DSP
                       pick the optimal value of the jitter buffer
                       size between the range of
                       cMediaGwCcCfgVbcJitterMaxDelay and
                       cMediaGwCcCfgVbcJitterMinDelay.
            
            fixed - means to use a constant jitter buffer size
                    which is specified by cMediaGwCcCfgVbdJitterNomDelay.";
          smiv2:defval "fixed";
          smiv2:max-access "read-write";
          smiv2:oid "1.3.6.1.4.1.9.9.324.1.1.7.1.6";
        }

        leaf cMediaGwCcCfgVbdJitterMaxDelay {
          type uint32 {
            range "20..135";
          }
          units "milliseconds";
          description
           "This object specifies the maximum jitter buffer size 
            in VBD (Voice Band Data)";
          smiv2:defval "135";
          smiv2:max-access "read-write";
          smiv2:oid "1.3.6.1.4.1.9.9.324.1.1.7.1.7";
        }

        leaf cMediaGwCcCfgVbdJitterNomDelay {
          type uint32 {
            range "5..135";
          }
          units "milliseconds";
          description
           "This object specifies the nominal jitter buffer size 
            in VBD (Voice Band Data)";
          smiv2:defval "70";
          smiv2:max-access "read-write";
          smiv2:oid "1.3.6.1.4.1.9.9.324.1.1.7.1.8";
        }

        leaf cMediaGwCcCfgVbdJitterMinDelay {
          type uint32 {
            range "0..135";
          }
          units "milliseconds";
          description
           "This object specifies the nominal jitter buffer size 
            in VBD (Voice Band Data)";
          smiv2:defval "0";
          smiv2:max-access "read-write";
          smiv2:oid "1.3.6.1.4.1.9.9.324.1.1.7.1.9";
        }

        leaf cMediaGwCcCfgDefaultTonePlanId {
          type CISCO-MEDIA-GATEWAY-MIB:CVoiceTonePlanIndex;
          description
           "This object specifies the default tone plan index
            (the value of cvtcTonePlanId) for the media gateway.";
          smiv2:defval "1";
          smiv2:max-access "read-write";
          smiv2:oid "1.3.6.1.4.1.9.9.324.1.1.7.1.10";
        }

        leaf cMediaGwCcCfgDescrInfoEnabled {
          type boolean;
          description
           "This object specifies whether the media gateway supports
            descriptive suffix of the name schema for terminations.
            
            There are two parts in name schema of termination, prefix
            and suffix. For example the name schema for a DS (Digital
            Subscriber) termination, can be 'DS/OC3_2/DS1_6/DS0_24'.
            It represents DS type termination in 2nd OC3 line, 
            6th DS1 and 24th DS0 channel. In this example, 'DS' is 
            the prefix, 'OC3_2/DS1_6/DS0_24' is the suffix.
            
            The name schema in above example has a descriptive suffix.
            The non-descriptive suffix for the same termination is 
            '2/6/24' and name schema becomes 'DS/2/6/24'.
            
            This object can not be modified if there is any termination
            existing in the media gateway.";
          smiv2:defval "false";
          smiv2:max-access "read-write";
          smiv2:oid "1.3.6.1.4.1.9.9.324.1.1.7.1.11";
        }

        leaf cMediaGwCcCfgDsNamePrefix {
          type snmp-framework:SnmpAdminString {
            length "1..64";
          }
          description
           "This object specifies the prefix of the name schema for
            DS (Digital Subscriber) terminations.
            The value of this object must be unique among the 
            following objects:
                   cMediaGwCcCfgDsNamePrefix
                   cMediaGwCcCfgRtpNamePrefix
                   cMediaGwCcCfgAal2SvcNamePrefix
                   cMediaGwCcCfgAal2SvcNamePrefix
                   cMediaGwCcCfgDefRtpNamePrefix
            This object can not be modified when there is any
            DS termination existing in the media gateway.
            It is default to 'DS'.";
          smiv2:defval "DS";
          smiv2:max-access "read-write";
          smiv2:oid "1.3.6.1.4.1.9.9.324.1.1.7.1.12";
        }

        leaf cMediaGwCcCfgRtpNamePrefix {
          type snmp-framework:SnmpAdminString {
            length "1..64";
          }
          description
           "This object specifies the prefix of the name schema for
            RTP (Real-Time Transport Protocol) terminations.
            The value of this object must be unique among the 
            following objects:
                   cMediaGwCcCfgDsNamePrefix
                   cMediaGwCcCfgRtpNamePrefix
                   cMediaGwCcCfgAal2SvcNamePrefix
                   cMediaGwCcCfgAal2SvcNamePrefix
                   cMediaGwCcCfgDefRtpNamePrefix
            This object can not be modified when there is any
            RTP termination type existing in the media gateway.
            It is default to 'RTP'.";
          smiv2:defval "RTP";
          smiv2:max-access "read-write";
          smiv2:oid "1.3.6.1.4.1.9.9.324.1.1.7.1.13";
        }

        leaf cMediaGwCcCfgAal1SvcNamePrefix {
          type snmp-framework:SnmpAdminString {
            length "1..64";
          }
          description
           "This object specifies the prefix of the name schema for
            voice over AAL1 SVC (Switched Virtual Circuit)
            terminations.
            The value of this object must be unique among the 
            following objects:
                   cMediaGwCcCfgDsNamePrefix
                   cMediaGwCcCfgRtpNamePrefix
                   cMediaGwCcCfgAal2SvcNamePrefix
                   cMediaGwCcCfgAal2SvcNamePrefix
                   cMediaGwCcCfgDefRtpNamePrefix
            This object can not be modified when there is any
            AAL1 SVC termination type existing in the media gateway.
            It is default to 'AAL1/SVC'.";
          smiv2:defval "AAL1/SVC";
          smiv2:max-access "read-write";
          smiv2:oid "1.3.6.1.4.1.9.9.324.1.1.7.1.14";
        }

        leaf cMediaGwCcCfgAal2SvcNamePrefix {
          type snmp-framework:SnmpAdminString {
            length "1..64";
          }
          description
           "This object specifies the prefix of the name schema for
            voice over AAL2 SVC (Switched Virtual Circuit)
            terminations.
            The value of this object must be unique among the 
            following objects:
                   cMediaGwCcCfgDsNamePrefix
                   cMediaGwCcCfgRtpNamePrefix
                   cMediaGwCcCfgAal2SvcNamePrefix
                   cMediaGwCcCfgAal2SvcNamePrefix
                   cMediaGwCcCfgDefRtpNamePrefix
            This object can not be modified when there is any
            AAL2 SVC termination type existing in the media gateway.
            It is default to 'AAL2/SVC'.";
          smiv2:defval "AAL2/SVC";
          smiv2:max-access "read-write";
          smiv2:oid "1.3.6.1.4.1.9.9.324.1.1.7.1.15";
        }

        leaf cMediaGwCcCfgClusterEnabled {
          type enumeration {
            enum "disabled" {
              value "1";
            }
            enum "enabled" {
              value "2";
            }
            enum "conditionalEnabled" {
              value "3";
            }
          }
          description
           "This object specifies the condition of the cluster generation
            in the call control.
            
            A cluster is a group of endpoints that share a particular
            bearer possibility for connections among each other.
            
            disabled(1) - The generation of the cluster attribute
                          is disabled.
            enabled(2) - Unconditionally generate the cluster
                         attribute.
            conditionalEnabled(3) - The generation of the cluster 
                          attribute is upon MGC request.";
          smiv2:defval "disabled";
          smiv2:max-access "read-write";
          smiv2:oid "1.3.6.1.4.1.9.9.324.1.1.7.1.16";
        }

        leaf cMediaGwCcCfgDefBearerTraffic {
          type enumeration {
            enum "ipPvcAal5" {
              value "1";
            }
            enum "atmPvcAal2" {
              value "2";
            }
            enum "atmSvcAal2" {
              value "3";
            }
            enum "atmSvcAal1" {
              value "4";
            }
          }
          description
           "This object specifies the combination of the network
            type (IP/ATM), virtual circuit type (PVC/SVC) and
            ATM adaptation layer type (AAL1/AAL2/AAL5) for the
            connection used in transporting bearer traffic.
            
                ipPvcAal5 (1) - The bearer traffic is transported in
                                IP network, through Permanent Virtual
                                Circuit(PVC) over AAL5 adaptation layer.
                atmPvcAal2 (2) - The bearer traffic is transported in
                                 ATM network, through Permanent Virtual
                                 Circuit(PVC) over AAL2 adaptation layer.
                atmSvcAal2 (3) - The bearer traffic is transported in
                                 ATM network, through Switching Virtual
                                 Circuit(SVC) over AAL2 adaptation layer.
                atmSvcAal1 (4) - The bearer traffic is transported in
                                 ATM network, through Switching Virtual
                                 Circuit(SVC) over AAL1 adaptation layer.
            
            In MGCP, if the call agent specifies the bear traffic type 
            in the local connection options (CRCX request), 
            configuration of this object will have no effect, 
            otherwise the value of this object will be used when 
            media gateway sending CRCX response.";
          smiv2:defval "ipPvcAal5";
          smiv2:max-access "read-write";
          smiv2:oid "1.3.6.1.4.1.9.9.324.1.1.7.1.17";
        }

        leaf cMediaGwCcCfgDefRtpNamePrefix {
          type snmp-framework:SnmpAdminString {
            length "1..64";
          }
          description
           "This object specifies the prefix of the name schema for
            default RTP terminations.
            The value of this object must be unique among the 
            following objects:
                   cMediaGwCcCfgDsNamePrefix
                   cMediaGwCcCfgRtpNamePrefix
                   cMediaGwCcCfgAal1SvcNamePrefix
                   cMediaGwCcCfgAal2SvcNamePrefix
            
            It is defaulted to 'TGWRTP'.";
          smiv2:defval "TGWRTP";
          smiv2:max-access "read-write";
          smiv2:oid "1.3.6.1.4.1.9.9.324.1.1.7.1.18";
        }
      }
    }

    container cMediaGwRscStatsTable {
      description
       "This table stores the gateway resource statistics
        information.";
      smiv2:oid "1.3.6.1.4.1.9.9.324.1.2.1";

      list cMediaGwRscStatsEntry {
        key "cmgwIndex cmgwRscStatsIndex";
        description
         "Each entry stores the statistics
          information for a specific resource.";
        smiv2:oid "1.3.6.1.4.1.9.9.324.1.2.1.1";

        leaf cmgwIndex {
          type leafref {
            path "/CISCO-MEDIA-GATEWAY-MIB:CISCO-MEDIA-GATEWAY-MIB/CISCO-MEDIA-GATEWAY-MIB:cMediaGwTable/CISCO-MEDIA-GATEWAY-MIB:cMediaGwEntry/CISCO-MEDIA-GATEWAY-MIB:cmgwIndex";
          }
        }

        leaf cmgwRscStatsIndex {
          type enumeration {
            enum "cpu" {
              value "1";
            }
            enum "staticmemory" {
              value "2";
            }
            enum "dynamicmemory" {
              value "3";
            }
            enum "sysmemory" {
              value "4";
            }
            enum "commbuffer" {
              value "5";
            }
            enum "msgq" {
              value "6";
            }
            enum "atmq" {
              value "7";
            }
            enum "svccongestion" {
              value "8";
            }
            enum "rsvpq" {
              value "9";
            }
            enum "dspq" {
              value "10";
            }
            enum "h248congestion" {
              value "11";
            }
            enum "callpersec" {
              value "12";
            }
            enum "smallipcbuffer" {
              value "13";
            }
            enum "mediumipcbuffer" {
              value "14";
            }
            enum "largeipcbuffer" {
              value "15";
            }
            enum "hugeipcbuffer" {
              value "16";
            }
            enum "mblkipcbuffer" {
              value "17";
            }
          }
          description
           "An index that uniquely identifies a specific gateway
            resource.";
          smiv2:max-access "not-accessible";
          smiv2:oid "1.3.6.1.4.1.9.9.324.1.2.1.1.1";
        }

        leaf cmgwRscMaximumUtilization {
          type yang:gauge32;
          description
           "This object indicates the maximum utilization of the
            resource over the interval specified by the
            'cmgwRscSinceLastReset'.";
          smiv2:max-access "read-only";
          smiv2:oid "1.3.6.1.4.1.9.9.324.1.2.1.1.2";
        }

        leaf cmgwRscMinimumUtilization {
          type yang:gauge32;
          description
           "This object indicates the minimum utilization of the
            resource over the interval specified by the
            'cmgwRscSinceLastReset'.";
          smiv2:max-access "read-only";
          smiv2:oid "1.3.6.1.4.1.9.9.324.1.2.1.1.3";
        }

        leaf cmgwRscAverageUtilization {
          type yang:gauge32;
          description
           "This object indicates the average utilization of the
            resource over the interval specified by the
            'cmgwRscSinceLastReset'.";
          smiv2:max-access "read-only";
          smiv2:oid "1.3.6.1.4.1.9.9.324.1.2.1.1.4";
        }

        leaf cmgwRscSinceLastReset {
          type uint32;
          units "seconds";
          description
           "The elapsed time (in seconds) from the last periodic reset.
            
            The following objects are reset at the last reset:
            
                'cmgwRscMaximumUtilization'
                'cmgwRscMinimumUtilization'
                'cmgwRscAverageUtilization'";
          smiv2:max-access "read-only";
          smiv2:oid "1.3.6.1.4.1.9.9.324.1.2.1.1.5";
        }
      }
    }
  }

  smiv2:alias "ciscoMediaGatewayMIB" {
    smiv2:oid "1.3.6.1.4.1.9.9.324";
  }

  smiv2:alias "ciscoMediaGatewayMIBNotifs" {
    smiv2:oid "1.3.6.1.4.1.9.9.324.0";
  }

  smiv2:alias "ciscoMediaGatewayMIBObjects" {
    smiv2:oid "1.3.6.1.4.1.9.9.324.1";
  }

  smiv2:alias "cMediaGwConfig" {
    smiv2:oid "1.3.6.1.4.1.9.9.324.1.1";
  }

  smiv2:alias "cMediaGwStats" {
    smiv2:oid "1.3.6.1.4.1.9.9.324.1.2";
  }

  smiv2:alias "cMediaGwMIBConformance" {
    smiv2:oid "1.3.6.1.4.1.9.9.324.2";
  }

  smiv2:alias "cMediaGwMIBCompliances" {
    smiv2:oid "1.3.6.1.4.1.9.9.324.2.1";
  }

  smiv2:alias "cMediaGwMIBGroups" {
    smiv2:oid "1.3.6.1.4.1.9.9.324.2.2";
  }

}
