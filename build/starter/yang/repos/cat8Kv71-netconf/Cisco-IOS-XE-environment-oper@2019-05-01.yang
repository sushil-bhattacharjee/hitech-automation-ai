module Cisco-IOS-XE-environment-oper {
  yang-version 1;
  namespace "http://cisco.com/ns/yang/Cisco-IOS-XE-environment-oper";
  prefix environment-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring Environment of a Network Element.
     Copyright (c) 2016-2019 by Cisco Systems, Inc.
     All rights reserved.";

  revision 2019-05-01 {
    description
      "Added semantic version";
    reference
      "2.2.0";
    cisco-semver:module-version "2.2.0";
  }
  revision 2018-10-29 {
    description
      "- A new field sensor type is added
       - Cleaned up spelling errors in descriptions.";
    reference
      "2.1.0";
    cisco-semver:module-version "2.1.0";
  }
  revision 2017-11-27 {
    description
      "Sensor thresholds. RPMs as units. Changed enumeration names to be lowercase and hyphenated";
    reference
      "2.0.0";
    cisco-semver:module-version "2.0.0";
  }
  revision 2017-02-07 {
    description
      "Initial revision";
    reference
      "1.0.0";
    cisco-semver:module-version "1.0.0";
  }

  typedef sensor-type {
    type enumeration {
      enum temperature {
        value 0;
      }
      enum voltage {
        value 1;
      }
      enum current {
        value 2;
      }
      enum power {
        value 3;
      }
      enum fan {
        value 4;
      }
      enum unknown-sensor {
        value 5;
      }
    }
    description
      "Type of the Sensor";
  }

  typedef sensor-units-type {
    type enumeration {
      enum watts {
        value 0;
      }
      enum celsius {
        value 1;
      }
      enum millivolts {
        value 2;
      }
      enum amperes {
        value 3;
      }
      enum volts-dc {
        value 4;
      }
      enum volts-ac {
        value 5;
      }
      enum milliamperes {
        value 6;
      }
      enum unknown {
        value 7;
      }
      enum revolutions-per-minute {
        value 8;
      }
    }
    description
      "Units used by various sensors";
  }

  grouping sensor-name-loc-key {
    description
      "Each sensor representing a data node is
       uniquely identified by a name and a location based key";
    leaf name {
      type string;
      description
        "Name of the sensor component.
         This includes all physical components of the chassis -
         both fixed and pluggable";
    }
    leaf location {
      type string;
      description
        "Sensor location";
    }
  }

  grouping sensor-params {
    description
      "Sensor parameters";
    leaf state {
      type string;
      description
        "A description of the current state of the sensor";
    }
    leaf current-reading {
      type uint32;
      description
        "Numerical value of the current sensor reading in sensor-units";
    }
    leaf sensor-units {
      type environment-ios-xe-oper:sensor-units-type;
      description
        "Units corresponding to the current-reading value";
    }
    leaf low-critical-threshold {
      type int32;
      description
        "Alarm threshold under which a critical
         alarm will be signalled";
    }
    leaf low-normal-threshold {
      type int32;
      description
        "No alarm above this threshold";
    }
    leaf high-normal-threshold {
      type int32;
      description
        "No alarm below this threshold";
    }
    leaf high-critical-threshold {
      type int32;
      description
        "Alarm threshold over which a critical
         alarm will be signalled";
    }
    leaf sensor-name {
      type environment-ios-xe-oper:sensor-type;
      description
        "Name of the Sensor";
    }
  }

  container environment-sensors {
    config false;
    description
      "Data nodes for Environmental Monitoring";
    list environment-sensor {
      key "name location";
      description
        "The list of components on the device chassis";
      uses environment-ios-xe-oper:sensor-params;
      uses environment-ios-xe-oper:sensor-name-loc-key;
    }
  }
}
