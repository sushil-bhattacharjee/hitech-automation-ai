module Cisco-IOS-XE-ppp-oper {
  yang-version 1;
  namespace "http://cisco.com/ns/yang/Cisco-IOS-XE-ppp-oper";
  prefix ppp-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for PPP and PPPoE operational data.
     Copyright (c) 2017-2019 by Cisco Systems, Inc.
     All rights reserved.";

  revision 2019-05-01 {
    description
      "Added semantic version";
    reference
      "1.3.0";
    cisco-semver:module-version "1.3.0";
  }
  revision 2018-10-29 {
    description
      "Cleaned up spelling errors in descriptions.";
    reference
      "1.2.0";
    cisco-semver:module-version "1.2.0";
  }
  revision 2018-02-19 {
    description
      "Addition of PPPoE statistics with padt and invalid discovery packet";
    reference
      "1.1.0";
    cisco-semver:module-version "1.1.0";
  }
  revision 2017-11-01 {
    description
      "Initial revision";
    reference
      "1.0.0";
    cisco-semver:module-version "1.0.0";
  }

  typedef ppp-ios-auth-type {
    type enumeration {
      enum ppp-ios-auth-none {
        value 0;
        description
          "No authentication.";
      }
      enum ppp-ios-auth-chap {
        value 1;
        description
          "Challenge Handshake Authentication (CHAP).";
      }
      enum ppp-ios-auth-pap {
        value 2;
        description
          "Password Authentication Protocol (PAP).";
      }
      enum ppp-ios-auth-mschap {
        value 3;
        description
          "Microsoft CHAP (MS CHAP).";
      }
      enum ppp-ios-auth-mschap-v2 {
        value 4;
        description
          "Microsoft CHAP, Version 2 (MS CHAP V2).";
      }
      enum ppp-ios-auth-eap {
        value 5;
        description
          "Extensible Authentication Protocol (EAP).";
      }
    }
    description
      "Authentication type for the PPP session";
  }

  typedef pppoe-operational-role {
    type enumeration {
      enum pppoe-client {
        value 0;
        description
          "PPPoE device role is a client";
      }
      enum pppoe-server {
        value 1;
        description
          "PPPoE device role is a server";
      }
    }
    description
      "The role that this PPPoE session is in";
  }

  grouping ppp-virtual-access-interface {
    description
      "The virtual access interface associated with the PPP session";
    leaf va-ifname {
      type string;
      description
        "PPP Virtual Access Interface Name";
    }
    leaf vrf-name {
      type string;
      description
        "VRF of Virtual Access Interface";
    }
    leaf interface-ip {
      type inet:ip-address;
      description
        "IP Address assigned/negotiated by PPP";
    }
    leaf gateway-ip {
      type inet:ip-address;
      description
        "Gateway IP Address assigned/negotiated by PPP";
    }
    leaf primary-dns-ip {
      type inet:ip-address;
      description
        "Primary DNS IP Address assigned/negotiated by PPP";
    }
    leaf secondary-dns-ip {
      type inet:ip-address;
      description
        "Secondary DNS IP Address assigned/negotiated by PPP";
    }
    leaf mtu {
      type uint32;
      description
        "MTU for PPP interface";
    }
    leaf auth-type {
      type ppp-ios-xe-oper:ppp-ios-auth-type;
      description
        "Authentication type for PPP interface";
    }
  }

  grouping ppp-interface {
    description
      "The PPP interface";
    leaf phy-ifname {
      type string;
      description
        "Ifname of Physical Access (Parent) Interface ";
    }
    list ppp-va {
      description
        "List of PPPoE sessions on ifname Physical access interface";
      uses ppp-ios-xe-oper:ppp-virtual-access-interface;
    }
  }

  grouping ppp-statistics {
    description
      "PPP global statistics";
    leaf ppp-lcp-pkts {
      type uint32;
      description
        "number of PPP LCP packets";
    }
    leaf ppp-ipcp-pkts {
      type uint32;
      description
        "number of PPP NCP/IPCP packets";
    }
    leaf ppp-ccp-pkts {
      type uint32;
      description
        "number of PPP CCP packets";
    }
  }

  grouping pppoe-session {
    description
      "PPPoE session information";
    leaf session-id {
      type uint16;
      description
        "Session Id of PPPoE sessions";
    }
    leaf lmac {
      type yang:mac-address;
      description
        "Local MAC Address";
    }
    leaf rmac {
      type yang:mac-address;
      description
        "Peer MAC Address";
    }
    leaf va-ifname {
      type string;
      description
        "Ifname of Virtual Access Interface";
    }
    leaf vrf-name {
      type string;
      description
        "VRF of Virtual Access Interface ";
    }
    leaf dot1q-qinq-outer-vlan {
      type uint16;
      description
        "PPPoE session VLAN/QinQ ID
         Outer VLAN (QinQ) or only VLAN ID";
    }
    leaf dot1q-qinq-inner-vlan {
      type uint16;
      description
        "PPPoE session VLAN/QinQ ID
         Inner VLAN ID (QinQ) (if valid)";
    }
    leaf service-name {
      type string;
      description
        "PPPoE service tag name";
    }
    leaf in-packet {
      type uint32;
      description
        "Number of packets received over session";
    }
    leaf out-packet {
      type uint32;
      description
        "Number of packets sent over session";
    }
    leaf in-bytes {
      type uint64;
      description
        "Number of bytes received over session";
    }
    leaf out-bytes {
      type uint64;
      description
        "Number of bytes sent over session";
    }
  }

  grouping pppoe-session-list {
    description
      "A list of PPPoE sessions";
    leaf ifname {
      type string;
      description
        "Ifname of Physical Access (Parent) Interface";
    }
    list session {
      description
        "List of PPPoE session on ifname Physical access interface";
      uses ppp-ios-xe-oper:pppoe-session;
    }
  }

  grouping pppoe-statistics {
    description
      "Global PPPoE statistics";
    leaf pppoe-padi-pkts {
      type uint32;
      description
        "PPPoE active discovery initiation packets";
    }
    leaf pppoe-pado-pkts {
      type uint32;
      description
        "PPPoE active discovery offer packets";
    }
    leaf pppoe-padr-pkts {
      type uint32;
      description
        "PPPoE active discovery response packets";
    }
    leaf pppoe-pads-pkts {
      type uint32;
      description
        "PPPoE active discovery session packets";
    }
    leaf pppoe-padt-pkts {
      type uint32;
      description
        "PPPoE active discovery terminate packets";
    }
    leaf invalid-discovery-pkts {
      type uint32;
      description
        "PPPoE invalid discovery packets";
    }
  }

  grouping pppoe {
    description
      "PPPoE information";
    leaf role {
      type ppp-ios-xe-oper:pppoe-operational-role;
      description
        "The current PPPoE role";
    }
    list pppoe-session-list {
      key "ifname";
      description
        "PPPoE session list";
      uses ppp-ios-xe-oper:pppoe-session-list;
    }
    container pppoe-statistics {
      presence "pppoe-statistics";
      description
        "PPPoE statistics";
      uses ppp-ios-xe-oper:pppoe-statistics;
    }
  }

  container ppp-data {
    config false;
    description
      "Operational state of PPP";
    list ppp-interface {
      key "phy-ifname";
      description
        "A list of the PPP information";
      uses ppp-ios-xe-oper:ppp-interface;
    }
    container ppp-statistics {
      presence "ppp-statistics";
      description
        "The PPP statistics";
      uses ppp-ios-xe-oper:ppp-statistics;
    }
    container pppoe {
      presence "pppoe";
      description
        "The PPPoE operation information";
      uses ppp-ios-xe-oper:pppoe;
    }
  }
}
