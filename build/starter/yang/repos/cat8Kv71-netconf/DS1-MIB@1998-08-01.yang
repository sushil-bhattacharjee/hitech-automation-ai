/*
 * Generated by confdc --mib2yang-std
 * Source: mgmt/dmi/model/mib/src/DS1-MIB.mib
 */
/*
 * This YANG module has been generated by smidump 0.5.0:
 *
 *      smidump -f yang DS1-MIB
 *
 * Do not edit. Edit the source file instead!
 */

module DS1-MIB {

  namespace "urn:ietf:params:xml:ns:yang:smiv2:DS1-MIB";
  prefix DS1-MIB;

  import IF-MIB {
    prefix "if-mib";
  }

  import PerfHist-TC-MIB {
    prefix "perfhist-tc";
  }

  import SNMPv2-TC {
    prefix "snmpv2-tc";
  }

  import ietf-yang-smiv2 {
    prefix "smiv2";
  }

  import ietf-yang-types {
    prefix "yang";
  }

  organization
   "IETF Trunk MIB Working Group";

  contact
   "        David Fowler
    
    Postal: Newbridge Networks Corporation
            600 March Road
            Kanata, Ontario, Canada K2K 2E6
    
            Tel: +1 613 591 3600
            Fax: +1 613 599 3667
    
    E-mail: davef@newbridge.com";

  description
   "The MIB module to describe DS1, E1, DS2, and
    E2 interfaces objects.";

  revision 1998-08-01 {
    description
     "[Revision added by libsmi due to a LAST-UPDATED clause.]";
  }


  container DS1-MIB {
    config false;

    container dsx1ConfigTable {
      description
       "The DS1 Configuration table.";
      smiv2:oid "1.3.6.1.2.1.10.18.6";

      list dsx1ConfigEntry {
        key "dsx1LineIndex";
        description
         "An entry in the DS1 Configuration table.";
        smiv2:oid "1.3.6.1.2.1.10.18.6.1";

        leaf dsx1LineIndex {
          type if-mib:InterfaceIndex;
          description
           "This object should be made equal to ifIndex.  The
            next paragraph describes its previous usage.
            Making the object equal to ifIndex allows proper
            use of ifStackTable and ds0/ds0bundle mibs.
            
            Previously, this object is the identifier of a DS1
            Interface on a managed device.  If there is an
            ifEntry that is directly associated with this and
            only this DS1 interface, it should have the same
            value as ifIndex.  Otherwise, number the
            dsx1LineIndices with an unique identifier
            following the rules of choosing a number that is
            greater than ifNumber and numbering the inside
            interfaces (e.g., equipment side) with even
            numbers and outside interfaces (e.g, network side)
            with odd numbers.";
          smiv2:max-access "read-only";
          smiv2:oid "1.3.6.1.2.1.10.18.6.1.1";
        }

        leaf dsx1IfIndex {
          type if-mib:InterfaceIndex;
          status deprecated;
          description
           "This value for this object is equal to the value
            of ifIndex from the Interfaces table of MIB II
            (RFC 1213).";
          smiv2:max-access "read-only";
          smiv2:oid "1.3.6.1.2.1.10.18.6.1.2";
        }

        leaf dsx1TimeElapsed {
          type int32 {
            range "0..899";
          }
          description
           "The number of seconds that have elapsed since
            the beginning of the near end current error-
            measurement period.  If, for some reason, such
            as an adjustment in the system's time-of-day
            clock, the current interval exceeds the maximum
            value, the agent will return the maximum value.";
          smiv2:max-access "read-only";
          smiv2:oid "1.3.6.1.2.1.10.18.6.1.3";
        }

        leaf dsx1ValidIntervals {
          type int32 {
            range "0..96";
          }
          description
           "The number of previous near end intervals for
            which data was collected.  The value will be
            96 unless the interface was brought online within
            the last 24 hours, in which case the value will be
            the number of complete 15 minute near end
            intervals since the interface has been online.  In
            the case where the agent is a proxy, it is
            possible that some intervals are unavailable.  In
            this case, this interval is the maximum interval
            number for which data is available.";
          smiv2:max-access "read-only";
          smiv2:oid "1.3.6.1.2.1.10.18.6.1.4";
        }

        leaf dsx1LineType {
          type enumeration {
            enum "other" {
              value "1";
            }
            enum "dsx1ESF" {
              value "2";
            }
            enum "dsx1D4" {
              value "3";
            }
            enum "dsx1E1" {
              value "4";
            }
            enum "dsx1E1CRC" {
              value "5";
            }
            enum "dsx1E1MF" {
              value "6";
            }
            enum "dsx1E1CRCMF" {
              value "7";
            }
            enum "dsx1Unframed" {
              value "8";
            }
            enum "dsx1E1Unframed" {
              value "9";
            }
            enum "dsx1DS2M12" {
              value "10";
            }
            enum "dsx2E2" {
              value "11";
            }
          }
          description
           "This variable indicates  the  variety  of  DS1
            Line  implementing  this  circuit.  The type of
            circuit affects the number of bits  per  second
            that  the circuit can reasonably carry, as well
            as the interpretation of the  usage  and  error
            statistics.  The values, in sequence, describe:
            
            TITLE:         SPECIFICATION:
            dsx1ESF         Extended SuperFrame DS1 (T1.107)
            dsx1D4          AT&T D4 format DS1 (T1.107)
            dsx1E1          ITU-T Recommendation G.704
                             (Table 4a)
            dsx1E1-CRC      ITU-T Recommendation G.704
                             (Table 4b)
            dsxE1-MF        G.704 (Table 4a) with TS16
                             multiframing enabled
            dsx1E1-CRC-MF   G.704 (Table 4b) with TS16
                             multiframing enabled
            dsx1Unframed    DS1 with No Framing
            dsx1E1Unframed  E1 with No Framing (G.703)
            dsx1DS2M12      DS2 frame format (T1.107)
            dsx1E2          E2 frame format (G.704)
            
            For clarification, the capacity for each E1 type
            is as listed below:
            dsx1E1Unframed - E1, no framing = 32 x 64k = 2048k
            dsx1E1 or dsx1E1CRC - E1, with framing,
               no signalling = 31 x 64k = 1984k
            dsx1E1MF or dsx1E1CRCMF - E1, with framing,
               signalling = 30 x 64k = 1920k
            
            For further information See ITU-T Recomm G.704";
          smiv2:max-access "read-write";
          smiv2:oid "1.3.6.1.2.1.10.18.6.1.5";
        }

        leaf dsx1LineCoding {
          type enumeration {
            enum "dsx1JBZS" {
              value "1";
            }
            enum "dsx1B8ZS" {
              value "2";
            }
            enum "dsx1HDB3" {
              value "3";
            }
            enum "dsx1ZBTSI" {
              value "4";
            }
            enum "dsx1AMI" {
              value "5";
            }
            enum "other" {
              value "6";
            }
            enum "dsx1B6ZS" {
              value "7";
            }
          }
          description
           "This variable describes the variety of Zero Code
            Suppression used on this interface, which in turn
            affects a number of its characteristics.
            
            dsx1JBZS refers the Jammed Bit Zero Suppression,
            in which the AT&T specification of at least one
            pulse every 8 bit periods is literally implemented
            by forcing a pulse in bit 8 of each channel.
            Thus, only seven bits per channel, or 1.344 Mbps,
            is available for data.
            
            dsx1B8ZS refers to the use of a specified pattern
            of normal bits and bipolar violations which are
            used to replace a sequence of eight zero bits.
            
            ANSI Clear Channels may use dsx1ZBTSI, or Zero
            Byte Time Slot Interchange.
            
            E1 links, with or without CRC, use dsx1HDB3 or
            dsx1AMI.
            
            dsx1AMI refers to a mode wherein no zero code
            suppression is present and the line encoding does
            not solve the problem directly.  In this
            application, the higher layer must provide data
            which meets or exceeds the pulse density
            requirements, such as inverting HDLC data.
            
            dsx1B6ZS refers to the user of a specifed pattern
            of normal bits and bipolar violations which are
            used to replace a sequence of six zero bits.  Used
            for DS2.";
          smiv2:max-access "read-write";
          smiv2:oid "1.3.6.1.2.1.10.18.6.1.6";
        }

        leaf dsx1SendCode {
          type enumeration {
            enum "dsx1SendNoCode" {
              value "1";
            }
            enum "dsx1SendLineCode" {
              value "2";
            }
            enum "dsx1SendPayloadCode" {
              value "3";
            }
            enum "dsx1SendResetCode" {
              value "4";
            }
            enum "dsx1SendQRS" {
              value "5";
            }
            enum "dsx1Send511Pattern" {
              value "6";
            }
            enum "dsx1Send3in24Pattern" {
              value "7";
            }
            enum "dsx1SendOtherTestPattern" {
              value "8";
            }
          }
          description
           "This variable indicates what type of code is
            being sent across the DS1 interface by the device.
            Setting this variable causes the interface to send
            the code requested.  The values mean:
            dsx1SendNoCode
            sending looped or normal data
            
            dsx1SendLineCode
            sending a request for a line loopback
            
            dsx1SendPayloadCode
            sending a request for a payload loopback
            
            dsx1SendResetCode
            sending a loopback termination request
            
            dsx1SendQRS
            sending a Quasi-Random Signal  (QRS)  test
            pattern
            
            dsx1Send511Pattern
            sending a 511 bit fixed test pattern
            
            dsx1Send3in24Pattern
            sending a fixed test pattern of 3 bits set
            in 24
            
            dsx1SendOtherTestPattern
            sending a test pattern  other  than  those
            described by this object";
          smiv2:max-access "read-write";
          smiv2:oid "1.3.6.1.2.1.10.18.6.1.7";
        }

        leaf dsx1CircuitIdentifier {
          type snmpv2-tc:DisplayString {
            length "0..255";
          }
          description
           "This variable contains the transmission vendor's
            circuit identifier, for the purpose of
            facilitating troubleshooting.";
          smiv2:max-access "read-write";
          smiv2:oid "1.3.6.1.2.1.10.18.6.1.8";
        }

        leaf dsx1LoopbackConfig {
          type enumeration {
            enum "dsx1NoLoop" {
              value "1";
            }
            enum "dsx1PayloadLoop" {
              value "2";
            }
            enum "dsx1LineLoop" {
              value "3";
            }
            enum "dsx1OtherLoop" {
              value "4";
            }
            enum "dsx1InwardLoop" {
              value "5";
            }
            enum "dsx1DualLoop" {
              value "6";
            }
          }
          description
           "This variable represents the desired loopback
            configuration of the DS1 interface.  Agents
            supporting read/write access should return
            inconsistentValue in response to a requested
            loopback state that the interface does not
            support.  The values mean:
            
            dsx1NoLoop
             Not in the loopback state.  A device that is not
            capable of performing a loopback on the interface
            shall always return this as its value.
            
            dsx1PayloadLoop
             The received signal at this interface is looped
            through the device.  Typically the received signal
            is looped back for retransmission after it has
            passed through the device's framing function.
            
            dsx1LineLoop
             The received signal at this interface does not go
            through the device (minimum penetration) but is
            looped back out.
            
            dsx1OtherLoop
             Loopbacks that are not defined here.
            
            dsx1InwardLoop
             The transmitted signal at this interface is
            looped back and received by the same interface.
            What is transmitted onto the line is product
            dependent.
            
            dsx1DualLoop
             Both dsx1LineLoop and dsx1InwardLoop will be
            active simultaneously.";
          smiv2:max-access "read-write";
          smiv2:oid "1.3.6.1.2.1.10.18.6.1.9";
        }

        leaf dsx1LineStatus {
          type int32 {
            range "1..131071";
          }
          description
           "This variable indicates the Line Status of the
            interface.  It contains loopback, failure,
            received 'alarm' and transmitted 'alarms
            information.
            
            The dsx1LineStatus is a bit map represented as a
            sum, therefore, it can represent multiple failures
            (alarms) and a LoopbackState simultaneously.
            
            dsx1NoAlarm must be set if and only if no other
            flag is set.
            
            If the dsx1loopbackState bit is set, the loopback
            in effect can be determined from the
            dsx1loopbackConfig object.
            The various bit positions are:
            1     dsx1NoAlarm           No alarm present
            2     dsx1RcvFarEndLOF      Far end LOF (a.k.a., Yellow Alarm)
            4     dsx1XmtFarEndLOF      Near end sending LOF Indication
            8     dsx1RcvAIS            Far end sending AIS
            16     dsx1XmtAIS            Near end sending AIS
            32     dsx1LossOfFrame       Near end LOF (a.k.a., Red Alarm)
            64     dsx1LossOfSignal      Near end Loss Of Signal
            128     dsx1LoopbackState     Near end is looped
            256     dsx1T16AIS            E1 TS16 AIS
            512     dsx1RcvFarEndLOMF     Far End Sending TS16 LOMF
            1024     dsx1XmtFarEndLOMF     Near End Sending TS16 LOMF
            2048     dsx1RcvTestCode       Near End detects a test code
            4096     dsx1OtherFailure      any line status not defined here
            8192     dsx1UnavailSigState   Near End in Unavailable Signal
                             State
            16384     dsx1NetEquipOOS       Carrier Equipment Out of Service
            32768     dsx1RcvPayloadAIS     DS2 Payload AIS
            65536     dsx1Ds2PerfThreshold  DS2 Performance Threshold
                             Exceeded";
          smiv2:max-access "read-only";
          smiv2:oid "1.3.6.1.2.1.10.18.6.1.10";
        }

        leaf dsx1SignalMode {
          type enumeration {
            enum "none" {
              value "1";
            }
            enum "robbedBit" {
              value "2";
            }
            enum "bitOriented" {
              value "3";
            }
            enum "messageOriented" {
              value "4";
            }
            enum "other" {
              value "5";
            }
          }
          description
           "'none' indicates that no bits are reserved for
            signaling on this channel.
            
            'robbedBit' indicates that DS1 Robbed Bit  Sig-
            naling is in use.
            
            'bitOriented' indicates that E1 Channel  Asso-
            ciated Signaling is in use.
            
            'messageOriented' indicates that Common  Chan-
            nel Signaling is in use either on channel 16 of
            an E1 link or channel 24 of a DS1.";
          smiv2:max-access "read-write";
          smiv2:oid "1.3.6.1.2.1.10.18.6.1.11";
        }

        leaf dsx1TransmitClockSource {
          type enumeration {
            enum "loopTiming" {
              value "1";
            }
            enum "localTiming" {
              value "2";
            }
            enum "throughTiming" {
              value "3";
            }
          }
          description
           "The source of Transmit Clock.
            'loopTiming' indicates that the recovered re-
            ceive clock is used as the transmit clock.
            
            'localTiming' indicates that a local clock
            source is used or when an external clock is
            attached to the box containing the interface.
            
            'throughTiming' indicates that recovered re-
            ceive clock from another interface is used as
            the transmit clock.";
          smiv2:max-access "read-write";
          smiv2:oid "1.3.6.1.2.1.10.18.6.1.12";
        }

        leaf dsx1Fdl {
          type int32 {
            range "1..15";
          }
          description
           "This bitmap describes the use of  the  facili-
            ties data link, and is the sum of the capabili-
            ties.  Set any bits that are appropriate:
            
            other(1),
            dsx1AnsiT1403(2),
            dsx1Att54016(4),
            dsx1FdlNone(8)
            
             'other' indicates that a protocol  other  than
            one following is used.
            
             'dsx1AnsiT1403' refers to the  FDL  exchange
            recommended by ANSI.
            
             'dsx1Att54016' refers to ESF FDL exchanges.
            
             'dsx1FdlNone' indicates that the device  does
            not use the FDL.";
          smiv2:max-access "read-write";
          smiv2:oid "1.3.6.1.2.1.10.18.6.1.13";
        }

        leaf dsx1InvalidIntervals {
          type int32 {
            range "0..96";
          }
          description
           "The number of intervals in the range from 0 to
            dsx1ValidIntervals for which no data is
            available.  This object will typically be zero
            except in cases where the data for some intervals
            are not available (e.g., in proxy situations).";
          smiv2:max-access "read-only";
          smiv2:oid "1.3.6.1.2.1.10.18.6.1.14";
        }

        leaf dsx1LineLength {
          type int32 {
            range "0..64000";
          }
          units "meters";
          description
           "The length of the ds1 line in meters. This
            objects provides information for line build out
            circuitry.  This object is only useful if the
            interface has configurable line build out
            circuitry.";
          smiv2:max-access "read-write";
          smiv2:oid "1.3.6.1.2.1.10.18.6.1.15";
        }

        leaf dsx1LineStatusLastChange {
          type yang:timestamp;
          description
           "The value of MIB II's sysUpTime object at the
            time this DS1 entered its current line status
            state.  If the current state was entered prior to
            the last re-initialization of the proxy-agent,
            then this object contains a zero value.";
          smiv2:max-access "read-only";
          smiv2:oid "1.3.6.1.2.1.10.18.6.1.16";
        }

        leaf dsx1LineStatusChangeTrapEnable {
          type enumeration {
            enum "enabled" {
              value "1";
            }
            enum "disabled" {
              value "2";
            }
          }
          description
           "Indicates whether dsx1LineStatusChange traps
            should be generated for this interface.";
          smiv2:defval "disabled";
          smiv2:max-access "read-write";
          smiv2:oid "1.3.6.1.2.1.10.18.6.1.17";
        }

        leaf dsx1LoopbackStatus {
          type int32 {
            range "1..127";
          }
          description
           "This variable represents the current state of the
            loopback on the DS1 interface.  It contains
            information about loopbacks established by a
            manager and remotely from the far end.
            
            The dsx1LoopbackStatus is a bit map represented as
            a sum, therefore is can represent multiple
            loopbacks simultaneously.
            
            The various bit positions are:
             1  dsx1NoLoopback
             2  dsx1NearEndPayloadLoopback
             4  dsx1NearEndLineLoopback
             8  dsx1NearEndOtherLoopback
            16  dsx1NearEndInwardLoopback
            32  dsx1FarEndPayloadLoopback
            64  dsx1FarEndLineLoopback";
          smiv2:max-access "read-only";
          smiv2:oid "1.3.6.1.2.1.10.18.6.1.18";
        }

        leaf dsx1Ds1ChannelNumber {
          type int32 {
            range "0..28";
          }
          description
           "This variable represents the channel number of
            the DS1/E1 on its parent Ds2/E2 or DS3/E3.  A
            value of 0 indicated this DS1/E1 does not have a
            parent DS3/E3.";
          smiv2:max-access "read-only";
          smiv2:oid "1.3.6.1.2.1.10.18.6.1.19";
        }

        leaf dsx1Channelization {
          type enumeration {
            enum "disabled" {
              value "1";
            }
            enum "enabledDs0" {
              value "2";
            }
            enum "enabledDs1" {
              value "3";
            }
          }
          description
           "Indicates whether this ds1/e1 is channelized or
            unchannelized.  The value of enabledDs0 indicates
            that this is a DS1 channelized into DS0s.  The
            value of enabledDs1 indicated that this is a DS2
            channelized into DS1s.  Setting this value will
            cause the creation or deletion of entries in the
            ifTable for the DS0s that are within the DS1.";
          smiv2:max-access "read-write";
          smiv2:oid "1.3.6.1.2.1.10.18.6.1.20";
        }
      }
    }

    container dsx1CurrentTable {
      description
       "The DS1 current table contains various statistics
        being collected for the current 15 minute
        interval.";
      smiv2:oid "1.3.6.1.2.1.10.18.7";

      list dsx1CurrentEntry {
        key "dsx1CurrentIndex";
        description
         "An entry in the DS1 Current table.";
        smiv2:oid "1.3.6.1.2.1.10.18.7.1";

        leaf dsx1CurrentIndex {
          type if-mib:InterfaceIndex;
          description
           "The index value which uniquely identifies  the
            DS1 interface to which this entry is applicable.
            The interface identified by a particular value of
            this index is the same interface as identified by
            the same value as a dsx1LineIndex object
            instance.";
          smiv2:max-access "read-only";
          smiv2:oid "1.3.6.1.2.1.10.18.7.1.1";
        }

        leaf dsx1CurrentESs {
          type perfhist-tc:PerfCurrentCount;
          description
           "The number of Errored Seconds.";
          smiv2:max-access "read-only";
          smiv2:oid "1.3.6.1.2.1.10.18.7.1.2";
        }

        leaf dsx1CurrentSESs {
          type perfhist-tc:PerfCurrentCount;
          description
           "The number of Severely Errored Seconds.";
          smiv2:max-access "read-only";
          smiv2:oid "1.3.6.1.2.1.10.18.7.1.3";
        }

        leaf dsx1CurrentSEFSs {
          type perfhist-tc:PerfCurrentCount;
          description
           "The number of Severely Errored Framing Seconds.";
          smiv2:max-access "read-only";
          smiv2:oid "1.3.6.1.2.1.10.18.7.1.4";
        }

        leaf dsx1CurrentUASs {
          type perfhist-tc:PerfCurrentCount;
          description
           "The number of Unavailable Seconds.";
          smiv2:max-access "read-only";
          smiv2:oid "1.3.6.1.2.1.10.18.7.1.5";
        }

        leaf dsx1CurrentCSSs {
          type perfhist-tc:PerfCurrentCount;
          description
           "The number of Controlled Slip Seconds.";
          smiv2:max-access "read-only";
          smiv2:oid "1.3.6.1.2.1.10.18.7.1.6";
        }

        leaf dsx1CurrentPCVs {
          type perfhist-tc:PerfCurrentCount;
          description
           "The number of Path Coding Violations.";
          smiv2:max-access "read-only";
          smiv2:oid "1.3.6.1.2.1.10.18.7.1.7";
        }

        leaf dsx1CurrentLESs {
          type perfhist-tc:PerfCurrentCount;
          description
           "The number of Line Errored Seconds.";
          smiv2:max-access "read-only";
          smiv2:oid "1.3.6.1.2.1.10.18.7.1.8";
        }

        leaf dsx1CurrentBESs {
          type perfhist-tc:PerfCurrentCount;
          description
           "The number of Bursty Errored Seconds.";
          smiv2:max-access "read-only";
          smiv2:oid "1.3.6.1.2.1.10.18.7.1.9";
        }

        leaf dsx1CurrentDMs {
          type perfhist-tc:PerfCurrentCount;
          description
           "The number of Degraded Minutes.";
          smiv2:max-access "read-only";
          smiv2:oid "1.3.6.1.2.1.10.18.7.1.10";
        }

        leaf dsx1CurrentLCVs {
          type perfhist-tc:PerfCurrentCount;
          description
           "The number of Line Code Violations (LCVs).";
          smiv2:max-access "read-only";
          smiv2:oid "1.3.6.1.2.1.10.18.7.1.11";
        }
      }
    }

    container dsx1IntervalTable {
      description
       "The DS1 Interval Table contains various
        statistics collected by each DS1 Interface over
        the previous 24 hours of operation.  The past 24
        hours are broken into 96 completed 15 minute
        intervals.  Each row in this table represents one
        such interval (identified by dsx1IntervalNumber)
        for one specific instance (identified by
        dsx1IntervalIndex).";
      smiv2:oid "1.3.6.1.2.1.10.18.8";

      list dsx1IntervalEntry {
        key "dsx1IntervalIndex dsx1IntervalNumber";
        description
         "An entry in the DS1 Interval table.";
        smiv2:oid "1.3.6.1.2.1.10.18.8.1";

        leaf dsx1IntervalIndex {
          type if-mib:InterfaceIndex;
          description
           "The index value which uniquely identifies the DS1
            interface to which this entry is applicable.  The
            interface identified by a particular value of this
            index is the same interface as identified by the
            same value as a dsx1LineIndex object instance.";
          smiv2:max-access "read-only";
          smiv2:oid "1.3.6.1.2.1.10.18.8.1.1";
        }

        leaf dsx1IntervalNumber {
          type int32 {
            range "1..96";
          }
          description
           "A number between 1 and 96, where 1 is the most
            recently completed 15 minute interval and 96 is
            the 15 minutes interval completed 23 hours and 45
            minutes prior to interval 1.";
          smiv2:max-access "read-only";
          smiv2:oid "1.3.6.1.2.1.10.18.8.1.2";
        }

        leaf dsx1IntervalESs {
          type perfhist-tc:PerfIntervalCount;
          description
           "The number of Errored Seconds.";
          smiv2:max-access "read-only";
          smiv2:oid "1.3.6.1.2.1.10.18.8.1.3";
        }

        leaf dsx1IntervalSESs {
          type perfhist-tc:PerfIntervalCount;
          description
           "The number of Severely Errored Seconds.";
          smiv2:max-access "read-only";
          smiv2:oid "1.3.6.1.2.1.10.18.8.1.4";
        }

        leaf dsx1IntervalSEFSs {
          type perfhist-tc:PerfIntervalCount;
          description
           "The number of Severely Errored Framing Seconds.";
          smiv2:max-access "read-only";
          smiv2:oid "1.3.6.1.2.1.10.18.8.1.5";
        }

        leaf dsx1IntervalUASs {
          type perfhist-tc:PerfIntervalCount;
          description
           "The number of Unavailable Seconds.  This object
            may decrease if the occurance of unavailable
            seconds occurs across an inteval boundary.";
          smiv2:max-access "read-only";
          smiv2:oid "1.3.6.1.2.1.10.18.8.1.6";
        }

        leaf dsx1IntervalCSSs {
          type perfhist-tc:PerfIntervalCount;
          description
           "The number of Controlled Slip Seconds.";
          smiv2:max-access "read-only";
          smiv2:oid "1.3.6.1.2.1.10.18.8.1.7";
        }

        leaf dsx1IntervalPCVs {
          type perfhist-tc:PerfIntervalCount;
          description
           "The number of Path Coding Violations.";
          smiv2:max-access "read-only";
          smiv2:oid "1.3.6.1.2.1.10.18.8.1.8";
        }

        leaf dsx1IntervalLESs {
          type perfhist-tc:PerfIntervalCount;
          description
           "The number of Line Errored Seconds.";
          smiv2:max-access "read-only";
          smiv2:oid "1.3.6.1.2.1.10.18.8.1.9";
        }

        leaf dsx1IntervalBESs {
          type perfhist-tc:PerfIntervalCount;
          description
           "The number of Bursty Errored Seconds.";
          smiv2:max-access "read-only";
          smiv2:oid "1.3.6.1.2.1.10.18.8.1.10";
        }

        leaf dsx1IntervalDMs {
          type perfhist-tc:PerfIntervalCount;
          description
           "The number of Degraded Minutes.";
          smiv2:max-access "read-only";
          smiv2:oid "1.3.6.1.2.1.10.18.8.1.11";
        }

        leaf dsx1IntervalLCVs {
          type perfhist-tc:PerfIntervalCount;
          description
           "The number of Line Code Violations.";
          smiv2:max-access "read-only";
          smiv2:oid "1.3.6.1.2.1.10.18.8.1.12";
        }

        leaf dsx1IntervalValidData {
          type boolean;
          description
           "This variable indicates if the data for this
            interval is valid.";
          smiv2:max-access "read-only";
          smiv2:oid "1.3.6.1.2.1.10.18.8.1.13";
        }
      }
    }

    container dsx1TotalTable {
      description
       "The DS1 Total Table contains the cumulative sum
        of the various statistics for the 24 hour period
        preceding the current interval.";
      smiv2:oid "1.3.6.1.2.1.10.18.9";

      list dsx1TotalEntry {
        key "dsx1TotalIndex";
        description
         "An entry in the DS1 Total table.";
        smiv2:oid "1.3.6.1.2.1.10.18.9.1";

        leaf dsx1TotalIndex {
          type if-mib:InterfaceIndex;
          description
           "The index value which uniquely identifies the DS1
            interface to which this entry is applicable.  The
            interface identified by a particular value of this
            index is the same interface as identified by the
            same value as a dsx1LineIndex object instance.";
          smiv2:max-access "read-only";
          smiv2:oid "1.3.6.1.2.1.10.18.9.1.1";
        }

        leaf dsx1TotalESs {
          type perfhist-tc:PerfTotalCount;
          description
           "The sum of Errored Seconds encountered by a DS1
            interface in the previous 24 hour interval.
            Invalid 15 minute intervals count as 0.";
          smiv2:max-access "read-only";
          smiv2:oid "1.3.6.1.2.1.10.18.9.1.2";
        }

        leaf dsx1TotalSESs {
          type perfhist-tc:PerfTotalCount;
          description
           "The number of Severely Errored Seconds
            encountered by a DS1 interface in the previous 24
            hour interval.  Invalid 15 minute intervals count
            as 0.";
          smiv2:max-access "read-only";
          smiv2:oid "1.3.6.1.2.1.10.18.9.1.3";
        }

        leaf dsx1TotalSEFSs {
          type perfhist-tc:PerfTotalCount;
          description
           "The number of Severely Errored Framing Seconds
            encountered by a DS1 interface in the previous 24
            hour interval.  Invalid 15 minute intervals count
            as 0.";
          smiv2:max-access "read-only";
          smiv2:oid "1.3.6.1.2.1.10.18.9.1.4";
        }

        leaf dsx1TotalUASs {
          type perfhist-tc:PerfTotalCount;
          description
           "The number of Unavailable Seconds encountered by
            a DS1 interface in the previous 24 hour interval.
            Invalid 15 minute intervals count as 0.";
          smiv2:max-access "read-only";
          smiv2:oid "1.3.6.1.2.1.10.18.9.1.5";
        }

        leaf dsx1TotalCSSs {
          type perfhist-tc:PerfTotalCount;
          description
           "The number of Controlled Slip Seconds encountered
            by a DS1 interface in the previous 24 hour
            interval.  Invalid 15 minute intervals count as
            0.";
          smiv2:max-access "read-only";
          smiv2:oid "1.3.6.1.2.1.10.18.9.1.6";
        }

        leaf dsx1TotalPCVs {
          type perfhist-tc:PerfTotalCount;
          description
           "The number of Path Coding Violations encountered
            by a DS1 interface in the previous 24 hour
            interval.  Invalid 15 minute intervals count as
            0.";
          smiv2:max-access "read-only";
          smiv2:oid "1.3.6.1.2.1.10.18.9.1.7";
        }

        leaf dsx1TotalLESs {
          type perfhist-tc:PerfTotalCount;
          description
           "The number of Line Errored Seconds encountered by
            a DS1 interface in the previous 24 hour interval.
            Invalid 15 minute intervals count as 0.";
          smiv2:max-access "read-only";
          smiv2:oid "1.3.6.1.2.1.10.18.9.1.8";
        }

        leaf dsx1TotalBESs {
          type perfhist-tc:PerfTotalCount;
          description
           "The number of Bursty Errored Seconds (BESs)
            encountered by a DS1 interface in the previous 24
            hour interval. Invalid 15 minute intervals count
            as 0.";
          smiv2:max-access "read-only";
          smiv2:oid "1.3.6.1.2.1.10.18.9.1.9";
        }

        leaf dsx1TotalDMs {
          type perfhist-tc:PerfTotalCount;
          description
           "The number of Degraded Minutes (DMs) encountered
            by a DS1 interface in the previous 24 hour
            interval.  Invalid 15 minute intervals count as
            0.";
          smiv2:max-access "read-only";
          smiv2:oid "1.3.6.1.2.1.10.18.9.1.10";
        }

        leaf dsx1TotalLCVs {
          type perfhist-tc:PerfTotalCount;
          description
           "The number of Line Code Violations (LCVs)
            encountered by a DS1 interface in the current 15
            minute interval.  Invalid 15 minute intervals
            count as 0.";
          smiv2:max-access "read-only";
          smiv2:oid "1.3.6.1.2.1.10.18.9.1.11";
        }
      }
    }

    container dsx1FarEndCurrentTable {
      description
       "The DS1 Far End Current table contains various
        statistics being collected for the current 15
        minute interval.  The statistics are collected
        from the far end messages on the Facilities Data
        Link.  The definitions are the same as described
        for the near-end information.";
      smiv2:oid "1.3.6.1.2.1.10.18.10";

      list dsx1FarEndCurrentEntry {
        key "dsx1FarEndCurrentIndex";
        description
         "An entry in the DS1 Far End Current table.";
        smiv2:oid "1.3.6.1.2.1.10.18.10.1";

        leaf dsx1FarEndCurrentIndex {
          type if-mib:InterfaceIndex;
          description
           "The index value which uniquely identifies the DS1
            interface to which this entry is applicable.  The
            interface identified by a particular value of this
            index is identical to the interface identified by
            the same value of dsx1LineIndex.";
          smiv2:max-access "read-only";
          smiv2:oid "1.3.6.1.2.1.10.18.10.1.1";
        }

        leaf dsx1FarEndTimeElapsed {
          type int32 {
            range "0..899";
          }
          description
           "The number of seconds that have elapsed since the
            beginning of the far end current error-measurement
            period.  If, for some reason, such as an
            adjustment in the system's time-of-day clock, the
            current interval exceeds the maximum value, the
            agent will return the maximum value.";
          smiv2:max-access "read-only";
          smiv2:oid "1.3.6.1.2.1.10.18.10.1.2";
        }

        leaf dsx1FarEndValidIntervals {
          type int32 {
            range "0..96";
          }
          description
           "The number of previous far end intervals for
            which data was collected.  The value will be
            96 unless the interface was brought online within
            the last 24 hours, in which case the value will be
            the number of complete 15 minute far end intervals
            since the interface has been online.";
          smiv2:max-access "read-only";
          smiv2:oid "1.3.6.1.2.1.10.18.10.1.3";
        }

        leaf dsx1FarEndCurrentESs {
          type perfhist-tc:PerfCurrentCount;
          description
           "The number of Far End Errored Seconds.";
          smiv2:max-access "read-only";
          smiv2:oid "1.3.6.1.2.1.10.18.10.1.4";
        }

        leaf dsx1FarEndCurrentSESs {
          type perfhist-tc:PerfCurrentCount;
          description
           "The number of Far End Severely Errored Seconds.";
          smiv2:max-access "read-only";
          smiv2:oid "1.3.6.1.2.1.10.18.10.1.5";
        }

        leaf dsx1FarEndCurrentSEFSs {
          type perfhist-tc:PerfCurrentCount;
          description
           "The number of Far End Severely Errored Framing
            Seconds.";
          smiv2:max-access "read-only";
          smiv2:oid "1.3.6.1.2.1.10.18.10.1.6";
        }

        leaf dsx1FarEndCurrentUASs {
          type perfhist-tc:PerfCurrentCount;
          description
           "The number of Unavailable Seconds.";
          smiv2:max-access "read-only";
          smiv2:oid "1.3.6.1.2.1.10.18.10.1.7";
        }

        leaf dsx1FarEndCurrentCSSs {
          type perfhist-tc:PerfCurrentCount;
          description
           "The number of Far End Controlled Slip Seconds.";
          smiv2:max-access "read-only";
          smiv2:oid "1.3.6.1.2.1.10.18.10.1.8";
        }

        leaf dsx1FarEndCurrentLESs {
          type perfhist-tc:PerfCurrentCount;
          description
           "The number of Far End Line Errored Seconds.";
          smiv2:max-access "read-only";
          smiv2:oid "1.3.6.1.2.1.10.18.10.1.9";
        }

        leaf dsx1FarEndCurrentPCVs {
          type perfhist-tc:PerfCurrentCount;
          description
           "The number of Far End Path Coding Violations.";
          smiv2:max-access "read-only";
          smiv2:oid "1.3.6.1.2.1.10.18.10.1.10";
        }

        leaf dsx1FarEndCurrentBESs {
          type perfhist-tc:PerfCurrentCount;
          description
           "The number of Far End Bursty Errored Seconds.";
          smiv2:max-access "read-only";
          smiv2:oid "1.3.6.1.2.1.10.18.10.1.11";
        }

        leaf dsx1FarEndCurrentDMs {
          type perfhist-tc:PerfCurrentCount;
          description
           "The number of Far End Degraded Minutes.";
          smiv2:max-access "read-only";
          smiv2:oid "1.3.6.1.2.1.10.18.10.1.12";
        }

        leaf dsx1FarEndInvalidIntervals {
          type int32 {
            range "0..96";
          }
          description
           "The number of intervals in the range from 0 to
            dsx1FarEndValidIntervals for which no data is
            available.  This object will typically be zero
            except in cases where the data for some intervals
            are not available (e.g., in proxy situations).";
          smiv2:max-access "read-only";
          smiv2:oid "1.3.6.1.2.1.10.18.10.1.13";
        }
      }
    }

    container dsx1FarEndIntervalTable {
      description
       "The DS1 Far End Interval Table contains various
        statistics collected by each DS1 interface over
        the previous 24 hours of operation.  The past 24
        hours are broken into 96 completed 15 minute
        intervals. Each row in this table represents one
        such interval (identified by
        dsx1FarEndIntervalNumber) for one specific
        instance (identified by dsx1FarEndIntervalIndex).";
      smiv2:oid "1.3.6.1.2.1.10.18.11";

      list dsx1FarEndIntervalEntry {
        key "dsx1FarEndIntervalIndex dsx1FarEndIntervalNumber";
        description
         "An entry in the DS1 Far End Interval table.";
        smiv2:oid "1.3.6.1.2.1.10.18.11.1";

        leaf dsx1FarEndIntervalIndex {
          type if-mib:InterfaceIndex;
          description
           "The index value which uniquely identifies the DS1
            interface to which this entry is applicable.  The
            interface identified by a particular value of this
            index is identical to the interface identified by
            the same value of dsx1LineIndex.";
          smiv2:max-access "read-only";
          smiv2:oid "1.3.6.1.2.1.10.18.11.1.1";
        }

        leaf dsx1FarEndIntervalNumber {
          type int32 {
            range "1..96";
          }
          description
           "A number between 1 and 96, where 1 is the most
            recently completed 15 minute interval and 96 is
            the 15 minutes interval completed 23 hours and 45
            minutes prior to interval 1.";
          smiv2:max-access "read-only";
          smiv2:oid "1.3.6.1.2.1.10.18.11.1.2";
        }

        leaf dsx1FarEndIntervalESs {
          type perfhist-tc:PerfIntervalCount;
          description
           "The number of Far End Errored Seconds.";
          smiv2:max-access "read-only";
          smiv2:oid "1.3.6.1.2.1.10.18.11.1.3";
        }

        leaf dsx1FarEndIntervalSESs {
          type perfhist-tc:PerfIntervalCount;
          description
           "The number of Far End Severely Errored Seconds.";
          smiv2:max-access "read-only";
          smiv2:oid "1.3.6.1.2.1.10.18.11.1.4";
        }

        leaf dsx1FarEndIntervalSEFSs {
          type perfhist-tc:PerfIntervalCount;
          description
           "The number of Far End Severely Errored Framing
            Seconds.";
          smiv2:max-access "read-only";
          smiv2:oid "1.3.6.1.2.1.10.18.11.1.5";
        }

        leaf dsx1FarEndIntervalUASs {
          type perfhist-tc:PerfIntervalCount;
          description
           "The number of Unavailable Seconds.";
          smiv2:max-access "read-only";
          smiv2:oid "1.3.6.1.2.1.10.18.11.1.6";
        }

        leaf dsx1FarEndIntervalCSSs {
          type perfhist-tc:PerfIntervalCount;
          description
           "The number of Far End Controlled Slip Seconds.";
          smiv2:max-access "read-only";
          smiv2:oid "1.3.6.1.2.1.10.18.11.1.7";
        }

        leaf dsx1FarEndIntervalLESs {
          type perfhist-tc:PerfIntervalCount;
          description
           "The number of Far End Line Errored Seconds.";
          smiv2:max-access "read-only";
          smiv2:oid "1.3.6.1.2.1.10.18.11.1.8";
        }

        leaf dsx1FarEndIntervalPCVs {
          type perfhist-tc:PerfIntervalCount;
          description
           "The number of Far End Path Coding Violations.";
          smiv2:max-access "read-only";
          smiv2:oid "1.3.6.1.2.1.10.18.11.1.9";
        }

        leaf dsx1FarEndIntervalBESs {
          type perfhist-tc:PerfIntervalCount;
          description
           "The number of Far End Bursty Errored Seconds.";
          smiv2:max-access "read-only";
          smiv2:oid "1.3.6.1.2.1.10.18.11.1.10";
        }

        leaf dsx1FarEndIntervalDMs {
          type perfhist-tc:PerfIntervalCount;
          description
           "The number of Far End Degraded Minutes.";
          smiv2:max-access "read-only";
          smiv2:oid "1.3.6.1.2.1.10.18.11.1.11";
        }

        leaf dsx1FarEndIntervalValidData {
          type boolean;
          description
           "This variable indicates if the data for this
            interval is valid.";
          smiv2:max-access "read-only";
          smiv2:oid "1.3.6.1.2.1.10.18.11.1.12";
        }
      }
    }

    container dsx1FarEndTotalTable {
      description
       "The DS1 Far End Total Table contains the
        cumulative sum of the various statistics for the
        24 hour period preceding the current interval.";
      smiv2:oid "1.3.6.1.2.1.10.18.12";

      list dsx1FarEndTotalEntry {
        key "dsx1FarEndTotalIndex";
        description
         "An entry in the DS1 Far End Total table.";
        smiv2:oid "1.3.6.1.2.1.10.18.12.1";

        leaf dsx1FarEndTotalIndex {
          type if-mib:InterfaceIndex;
          description
           "The index value which uniquely identifies the DS1
            interface to which this entry is applicable.  The
            interface identified by a particular value of this
            index is identical to the interface identified by
            the same value of dsx1LineIndex.";
          smiv2:max-access "read-only";
          smiv2:oid "1.3.6.1.2.1.10.18.12.1.1";
        }

        leaf dsx1FarEndTotalESs {
          type perfhist-tc:PerfTotalCount;
          description
           "The number of Far End Errored Seconds encountered
            by a DS1 interface in the previous 24 hour
            interval.  Invalid 15 minute intervals count as
            0.";
          smiv2:max-access "read-only";
          smiv2:oid "1.3.6.1.2.1.10.18.12.1.2";
        }

        leaf dsx1FarEndTotalSESs {
          type perfhist-tc:PerfTotalCount;
          description
           "The number of Far End Severely Errored Seconds
            encountered by a DS1 interface in the previous 24
            hour interval.  Invalid 15 minute intervals count
            as 0.";
          smiv2:max-access "read-only";
          smiv2:oid "1.3.6.1.2.1.10.18.12.1.3";
        }

        leaf dsx1FarEndTotalSEFSs {
          type perfhist-tc:PerfTotalCount;
          description
           "The number of Far End Severely Errored Framing
            Seconds encountered by a DS1 interface in the
            previous 24 hour interval. Invalid 15 minute
            intervals count as 0.";
          smiv2:max-access "read-only";
          smiv2:oid "1.3.6.1.2.1.10.18.12.1.4";
        }

        leaf dsx1FarEndTotalUASs {
          type perfhist-tc:PerfTotalCount;
          description
           "The number of Unavailable Seconds encountered by
            a DS1 interface in the previous 24 hour interval.
            Invalid 15 minute intervals count as 0.";
          smiv2:max-access "read-only";
          smiv2:oid "1.3.6.1.2.1.10.18.12.1.5";
        }

        leaf dsx1FarEndTotalCSSs {
          type perfhist-tc:PerfTotalCount;
          description
           "The number of Far End Controlled Slip Seconds
            encountered by a DS1 interface in the previous 24
            hour interval.  Invalid 15 minute intervals count
            as 0.";
          smiv2:max-access "read-only";
          smiv2:oid "1.3.6.1.2.1.10.18.12.1.6";
        }

        leaf dsx1FarEndTotalLESs {
          type perfhist-tc:PerfTotalCount;
          description
           "The number of Far End Line Errored Seconds
            encountered by a DS1 interface in the previous 24
            hour interval.  Invalid 15 minute intervals count
            as 0.";
          smiv2:max-access "read-only";
          smiv2:oid "1.3.6.1.2.1.10.18.12.1.7";
        }

        leaf dsx1FarEndTotalPCVs {
          type perfhist-tc:PerfTotalCount;
          description
           "The number of Far End Path Coding Violations
            reported via the far end block error count
            encountered by a DS1 interface in the previous 24
            hour interval.  Invalid 15 minute intervals count
            as 0.";
          smiv2:max-access "read-only";
          smiv2:oid "1.3.6.1.2.1.10.18.12.1.8";
        }

        leaf dsx1FarEndTotalBESs {
          type perfhist-tc:PerfTotalCount;
          description
           "The number of Bursty Errored Seconds (BESs)
            encountered by a DS1 interface in the previous 24
            hour interval. Invalid 15 minute intervals count
            as 0.";
          smiv2:max-access "read-only";
          smiv2:oid "1.3.6.1.2.1.10.18.12.1.9";
        }

        leaf dsx1FarEndTotalDMs {
          type perfhist-tc:PerfTotalCount;
          description
           "The number of Degraded Minutes (DMs) encountered
            by a DS1 interface in the previous 24 hour
            interval.  Invalid 15 minute intervals count as
            0.";
          smiv2:max-access "read-only";
          smiv2:oid "1.3.6.1.2.1.10.18.12.1.10";
        }
      }
    }

    container dsx1FracTable {
      status deprecated;
      description
       "This table is deprecated in favour of using
        ifStackTable.
        
        The table was mandatory for systems dividing a DS1
        into channels containing different data streams
        that are of local interest.  Systems which are
        indifferent to data content, such as CSUs, need
        not implement it.
        
        The DS1 fractional table identifies which DS1
        channels associated with a CSU are being used to
        support a logical interface, i.e., an entry in the
        interfaces table from the Internet-standard MIB.
        
        For example, consider an application managing a
        North American ISDN Primary Rate link whose
        division is a 384 kbit/s H1 _B_ Channel for Video,
        a second H1 for data to a primary routing peer,
        and 12 64 kbit/s H0 _B_ Channels. Consider that
        some subset of the H0 channels are used for voice
        and the remainder are available for dynamic data
        calls.
        
        We count a total of 14 interfaces multiplexed onto
        the DS1 interface. Six DS1 channels (for the sake
        of the example, channels 1..6) are used for Video,
        six more (7..11 and 13) are used for data, and the
        remaining 12 are are in channels 12 and 14..24.
        
        Let us further imagine that ifIndex 2 is of type
        DS1 and refers to the DS1 interface, and that the
        interfaces layered onto it are numbered 3..16.
        
        We might describe the allocation of channels, in
        the dsx1FracTable, as follows:
        dsx1FracIfIndex.2. 1 = 3  dsx1FracIfIndex.2.13 = 4
        dsx1FracIfIndex.2. 2 = 3  dsx1FracIfIndex.2.14 = 6
        dsx1FracIfIndex.2. 3 = 3  dsx1FracIfIndex.2.15 = 7
        dsx1FracIfIndex.2. 4 = 3  dsx1FracIfIndex.2.16 = 8
        dsx1FracIfIndex.2. 5 = 3  dsx1FracIfIndex.2.17 = 9
        dsx1FracIfIndex.2. 6 = 3  dsx1FracIfIndex.2.18 = 10
        dsx1FracIfIndex.2. 7 = 4  dsx1FracIfIndex.2.19 = 11
        dsx1FracIfIndex.2. 8 = 4  dsx1FracIfIndex.2.20 = 12
        dsx1FracIfIndex.2. 9 = 4  dsx1FracIfIndex.2.21 = 13
        dsx1FracIfIndex.2.10 = 4  dsx1FracIfIndex.2.22 = 14
        dsx1FracIfIndex.2.11 = 4  dsx1FracIfIndex.2.23 = 15
        dsx1FracIfIndex.2.12 = 5  dsx1FracIfIndex.2.24 = 16
        
        For North American (DS1) interfaces, there are 24
        legal channels, numbered 1 through 24.
        
        For G.704 interfaces, there are 31 legal channels,
        numbered 1 through 31.  The channels (1..31)
        correspond directly to the equivalently numbered
        time-slots.";
      smiv2:oid "1.3.6.1.2.1.10.18.13";

      list dsx1FracEntry {
        key "dsx1FracIndex dsx1FracNumber";
        status deprecated;
        description
         "An entry in the DS1 Fractional table.";
        smiv2:oid "1.3.6.1.2.1.10.18.13.1";

        leaf dsx1FracIndex {
          type int32 {
            range "1..2147483647";
          }
          status deprecated;
          description
           "The index value which uniquely identifies  the
            DS1  interface  to which this entry is applicable
            The interface identified by a  particular
            value  of  this  index is the same interface as
            identified by the same value  an  dsx1LineIndex
            object instance.";
          smiv2:max-access "read-only";
          smiv2:oid "1.3.6.1.2.1.10.18.13.1.1";
        }

        leaf dsx1FracNumber {
          type int32 {
            range "1..31";
          }
          status deprecated;
          description
           "The channel number for this entry.";
          smiv2:max-access "read-only";
          smiv2:oid "1.3.6.1.2.1.10.18.13.1.2";
        }

        leaf dsx1FracIfIndex {
          type int32 {
            range "1..2147483647";
          }
          status deprecated;
          description
           "An index value that uniquely identifies an
            interface.  The interface identified by a particular
            value of this index is the same  interface
            as  identified by the same value an ifIndex
            object instance. If no interface is currently using
            a channel, the value should be zero.  If a
            single interface occupies more  than  one  time
            slot,  that ifIndex value will be found in multiple
            time slots.";
          smiv2:max-access "read-write";
          smiv2:oid "1.3.6.1.2.1.10.18.13.1.3";
        }
      }
    }

    container dsx1ChanMappingTable {
      description
       "The DS1 Channel Mapping table.  This table maps a
        DS1 channel number on a particular DS3 into an
        ifIndex.  In the presence of DS2s, this table can
        be used to map a DS2 channel number on a DS3 into
        an ifIndex, or used to map a DS1 channel number on
        a DS2 onto an ifIndex.";
      smiv2:oid "1.3.6.1.2.1.10.18.16";

      list dsx1ChanMappingEntry {
        key "ifIndex dsx1Ds1ChannelNumber";
        description
         "An entry in the DS1 Channel Mapping table.  There
          is an entry in this table corresponding to each
          ds1 ifEntry within any interface that is
          channelized to the individual ds1 ifEntry level.
          
          This table is intended to facilitate mapping from
          channelized interface / channel number to DS1
          ifEntry.  (e.g. mapping (DS3 ifIndex, DS1 Channel
          Number) -> ifIndex)
          
          While this table provides information that can
          also be found in the ifStackTable and
          dsx1ConfigTable, it provides this same information
          with a single table lookup, rather than by walking
          the ifStackTable to find the various constituent
          ds1 ifTable entries, and testing various
          dsx1ConfigTable entries to check for the entry
          with the applicable DS1 channel number.";
        smiv2:oid "1.3.6.1.2.1.10.18.16.1";

        leaf ifIndex {
          type leafref {
            path "/if-mib:IF-MIB/if-mib:ifTable/if-mib:ifEntry/if-mib:ifIndex";
          }
        }

        leaf dsx1Ds1ChannelNumber {
          type leafref {
            path "/DS1-MIB:DS1-MIB/DS1-MIB:dsx1ConfigTable/DS1-MIB:dsx1ConfigEntry/DS1-MIB:dsx1Ds1ChannelNumber";
          }
        }

        leaf dsx1ChanMappedIfIndex {
          type if-mib:InterfaceIndex;
          description
           "This object indicates the ifIndex value assigned
            by the agent for the individual ds1 ifEntry that
            corresponds to the given DS1 channel number
            (specified by the INDEX element
            dsx1Ds1ChannelNumber) of the given channelized
            interface (specified by INDEX element ifIndex).";
          smiv2:max-access "read-only";
          smiv2:oid "1.3.6.1.2.1.10.18.16.1.1";
        }
      }
    }
  }

  notification dsx1LineStatusChange {
    description
     "A dsx1LineStatusChange trap is sent when the
      value of an instance dsx1LineStatus changes. It
      can be utilized by an NMS to trigger polls.  When
      the line status change results from a higher level
      line status change (i.e. ds3), then no traps for
      the ds1 are sent.";
    smiv2:oid "1.3.6.1.2.1.10.18.15.0.1";

    container object-1 {

      leaf dsx1LineIndex {
        type leafref {
          path "/DS1-MIB:DS1-MIB/DS1-MIB:dsx1ConfigTable/DS1-MIB:dsx1ConfigEntry/DS1-MIB:dsx1LineIndex";
        }
      }

      leaf dsx1LineStatus {
        type leafref {
          path "/DS1-MIB:DS1-MIB/DS1-MIB:dsx1ConfigTable/DS1-MIB:dsx1ConfigEntry/DS1-MIB:dsx1LineStatus";
        }
      }
    }

    container object-2 {

      leaf dsx1LineIndex {
        type leafref {
          path "/DS1-MIB:DS1-MIB/DS1-MIB:dsx1ConfigTable/DS1-MIB:dsx1ConfigEntry/DS1-MIB:dsx1LineIndex";
        }
      }

      leaf dsx1LineStatusLastChange {
        type leafref {
          path "/DS1-MIB:DS1-MIB/DS1-MIB:dsx1ConfigTable/DS1-MIB:dsx1ConfigEntry/DS1-MIB:dsx1LineStatusLastChange";
        }
      }
    }
  }

  smiv2:alias "ds1" {
    smiv2:oid "1.3.6.1.2.1.10.18";
  }

  smiv2:alias "ds1Conformance" {
    smiv2:oid "1.3.6.1.2.1.10.18.14";
  }

  smiv2:alias "ds1Groups" {
    smiv2:oid "1.3.6.1.2.1.10.18.14.1";
  }

  smiv2:alias "ds1Compliances" {
    smiv2:oid "1.3.6.1.2.1.10.18.14.2";
  }

  smiv2:alias "ds1Traps" {
    smiv2:oid "1.3.6.1.2.1.10.18.15";
  }

}
