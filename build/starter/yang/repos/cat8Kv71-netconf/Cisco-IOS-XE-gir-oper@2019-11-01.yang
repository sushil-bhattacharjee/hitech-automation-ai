module Cisco-IOS-XE-gir-oper {
  yang-version 1;
  namespace "http://cisco.com/ns/yang/Cisco-IOS-XE-gir-oper";
  prefix gir-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE maintenance mode (GIR) operational data.
     Copyright (c) 2018-2019 by Cisco Systems, Inc.
     All rights reserved.";

  revision 2019-11-01 {
    description
      "Update copyright";
    reference
      "1.2.1";
    cisco-semver:module-version "1.2.1";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-04-01 {
    description
      "Initial revision";
    reference
      "1.0.0";
    cisco-semver:module-version "1.0.0";
  }

  typedef gir-system-mode {
    type enumeration {
      enum gir-normal-mode {
        value 0;
        description
          "Normal operational mode";
      }
      enum gir-maintenance-mode {
        value 1;
        description
          "Maintenance mode";
      }
      enum gir-transition-into-mmode {
        value 2;
        description
          "Transition into maintenance mode";
      }
      enum gir-transition-out-mmode {
        value 3;
        description
          "Transition out of maintenance mode";
      }
    }
    description
      "The system mode this device is currently in";
  }

  typedef gir-transition-state {
    type enumeration {
      enum gir-client-transition-start {
        value 0;
        description
          "Transition started";
      }
      enum gir-client-transition-complete {
        value 1;
        description
          "Transition completed";
      }
      enum gir-client-transition-fail {
        value 2;
        description
          "Transition failed";
      }
      enum gir-client-transition-none {
        value 3;
        description
          "No transition has happened";
      }
    }
    description
      "Transition states of maintenance mode clients";
  }

  typedef gir-class-type {
    type enumeration {
      enum gir-client-class-egp {
        value 0;
        description
          "Exterior Gateway Protocols";
      }
      enum gir-client-class-igp {
        value 1;
        description
          "Interior Gateway Protocols";
      }
      enum gir-client-class-mcast {
        value 2;
        description
          "Multicast Protocols";
      }
      enum gir-client-class-fhrp {
        value 3;
        description
          "First Hop Redundancy Protocols";
      }
      enum gir-client-class-l2 {
        value 4;
        description
          "Layer 2 interface level protocols";
      }
    }
    description
      "Protocol class of maintenance mode clients";
  }

  grouping gir-counter {
    description
      "Maintenance mode global counters";
    leaf enter-mmode-without-tmpl-init {
      type uint64;
      description
        "Counter for initial process when entering maintenance mode without template";
    }
    leaf enter-mmode-tmpl-init {
      type uint64;
      description
        "Counter for initial process when entering maintenance mode with template";
    }
    leaf entered-mmode {
      type uint64;
      description
        "Counter for successfully entering maintenance mode";
    }
    leaf exit-mmode-init {
      type uint64;
      description
        "Counter for initial process when exiting maintenance mode";
    }
    leaf exited-mmode {
      type uint64;
      description
        "Counter for successfully exiting maintenance mode";
    }
    leaf stop-mmode-with-tmpl {
      type uint64;
      description
        "Counter for exiting maintenance mode with template";
    }
    leaf entered-mmode-tmpl {
      type uint64;
      description
        "Counter for entering maintenance mode with template";
    }
    leaf failsafe-exp {
      type uint64;
      description
        "Counter for failsafe timer expiration";
    }
    leaf timeout-exp {
      type uint64;
      description
        "Counter for timeout timer expiration";
    }
    leaf already-in-trans {
      type uint64;
      description
        "Counter for changing maintenance mode when already in transition";
    }
    leaf clients-registered {
      type uint64;
      description
        "Counter for number of times clients registered to maintenance mode subsystem";
    }
    leaf clients-deregistered {
      type uint64;
      description
        "Counter for number of times clients deregistered from maintenance mode subsystem";
    }
    leaf prc-yielded {
      type uint64;
      description
        "Counter for maintenance mode process yielded";
    }
    leaf sync-start-maintenance-sent {
      type uint64;
      description
        "Counter for sent sync messages when starting maintenance mode";
    }
    leaf sync-compl-maintenance-sent {
      type uint64;
      description
        "Counter for sent sync messages when completing maintenance mode";
    }
    leaf sync-start-maintenance-recvd {
      type uint64;
      description
        "Counter for received sync messages when starting maintenance mode";
    }
    leaf sync-compl-maintenance-recvd {
      type uint64;
      description
        "Counter for received sync messages when completing maintenance mode";
    }
    leaf reload-in-maintenance {
      type uint64;
      description
        "Counter for reload in maintenance mode";
    }
    leaf switch-over-in-trans-tmpl {
      type uint64;
      description
        "Counter for switchover in maintenance mode transition";
    }
    leaf stop-without-start {
      type uint64;
      description
        "Counter for stopping maintenance mode without starting";
    }
  }

  grouping gir-error-counter {
    description
      "Maintenance mode error counters";
    leaf chkpt {
      type uint64;
      description
        "Counter for errors during checkpoint";
    }
    leaf issu {
      type uint64;
      description
        "Counter for errors during In Service Software Upgrade";
    }
    leaf chunk {
      type uint64;
      description
        "Counter for errors during memory chuck allocation";
    }
    leaf snapshot {
      type uint64;
      description
        "Counter for errors during snapshot";
    }
    leaf mmode-cli {
      type uint64;
      description
        "Counter for errors during maintenance mode CLIs";
    }
    leaf mmode-client-class-invalid {
      type uint64;
      description
        "Counter for errors of maintenance mode client with invalid class";
    }
    leaf mmode-client-not-found {
      type uint64;
      description
        "Counter for errors of maintenance mode client not found";
    }
    leaf tmpl-not-found-class-client-list {
      type uint64;
      description
        "Counter for errors of maintenance mode template not found";
    }
    leaf add-tmpl-client-to-class-seq-failed {
      type uint64;
      description
        "Counter for errors of adding client to template sequence failed";
    }
    leaf add-client-to-seq {
      type uint64;
      description
        "Counter for errors of adding client to default sequence failed";
    }
    leaf invalid-input-args-dereg-client {
      type uint64;
      description
        "Counter for errors of invalid arguments during client deregister";
    }
    leaf dereg-client-of-type-not-found {
      type uint64;
      description
        "Counter for errors of client type not found during client deregister";
    }
    leaf invalid-arg-transition-mmode-client {
      type uint64;
      description
        "Counter for errors of invalid argument during client transition";
    }
    leaf transition-ack-recvd-invalid-class-seq {
      type uint64;
      description
        "Counter for errors of receiving invalid class sequence during maintenance mode transition";
    }
    leaf mmode-client-invalid-ack {
      type uint64;
      description
        "Counter for errors of invalid ack from client during maintenance mode transition";
    }
  }

  grouping gir-client-counter {
    description
      "Maintenance mode client counters";
    leaf start-isolate {
      type uint64;
      description
        "Counter for client starting isolation";
    }
    leaf start-insert {
      type uint64;
      description
        "Counter for client starting insertion";
    }
    leaf isolate-ack {
      type uint64;
      description
        "Counter for client ack during isolation";
    }
    leaf insert-ack {
      type uint64;
      description
        "Counter for client ack during insertion";
    }
    leaf isolate-nack {
      type uint64;
      description
        "Counter for client nack during isolation";
    }
    leaf insert-nack {
      type uint64;
      description
        "Counter for client nack during insertion";
    }
  }

  grouping gir-client-params {
    description
      "Maintenance mode client parameters";
    leaf client-name {
      type string;
      description
        "Maintenance mode client name";
    }
    leaf class-type {
      type gir-ios-xe-oper:gir-class-type;
      description
        "Maintenance mode client class type";
    }
    leaf transition-state {
      type gir-ios-xe-oper:gir-transition-state;
      description
        "Maintenance mode client transition state";
    }
    container gir-client-counters {
      description
        "Maintenance mode client counters";
      uses gir-ios-xe-oper:gir-client-counter;
    }
  }

  grouping gir-global-params {
    description
      "Maintenance mode global parameters";
    leaf reload-in-maintenance {
      type boolean;
      description
        "next reload into maintenance mode";
    }
    leaf template-name {
      type string;
      description
        "Maintenance mode template name";
    }
    leaf mmode-timeout {
      type uint32;
      description
        "Maintenance mode timeout value";
    }
    leaf mmode-duration {
      type uint32;
      description
        "Maintenance mode current duration";
    }
    leaf system-mode {
      type gir-ios-xe-oper:gir-system-mode;
      description
        "Current system mode";
    }
    container gir-counters {
      description
        "Maintenance mode counters";
      uses gir-ios-xe-oper:gir-counter;
    }
    container gir-error-counters {
      description
        "Maintenance mode error counters";
      uses gir-ios-xe-oper:gir-error-counter;
    }
    list gir-clients {
      key "client-name";
      description
        "Maintenance mode client list";
      uses gir-ios-xe-oper:gir-client-params;
    }
  }

  container gir-oper-data {
    config false;
    description
      "Maintenance mode operational data";
    container gir-globals {
      presence "gir-globals";
      description
        "Maintenance mode global data";
      uses gir-ios-xe-oper:gir-global-params;
    }
  }
}
