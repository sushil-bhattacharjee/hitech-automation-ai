/*
 * Generated by confdc --mib2yang-std
 * Source: mgmt/dmi/model/mib/src/RFC-1215.mib
 */
/*
 * This YANG module has been generated by smidump 0.5.0:
 *
 *      smidump -f yang RFC-1215
 *
 * Do not edit. Edit the source file instead!
 */

module RFC-1215 {

  namespace "urn:ietf:params:xml:ns:yang:smiv2:RFC-1215";
  prefix RFC-1215;

  import ietf-yang-smiv2 {
    prefix "smiv2";
  }

}
