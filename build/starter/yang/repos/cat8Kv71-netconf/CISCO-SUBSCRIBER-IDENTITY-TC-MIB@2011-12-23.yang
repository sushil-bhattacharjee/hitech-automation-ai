/*
 * Generated by confdc --mib2yang-std
 * Source: mgmt/dmi/model/mib/src/CISCO-SUBSCRIBER-IDENTITY-TC-MIB.mib
 */
/*
 * This YANG module has been generated by smidump 0.5.0:
 *
 *      smidump -f yang CISCO-SUBSCRIBER-IDENTITY-TC-MIB
 *
 * Do not edit. Edit the source file instead!
 */

module CISCO-SUBSCRIBER-IDENTITY-TC-MIB {

  namespace "urn:ietf:params:xml:ns:yang:smiv2:CISCO-SUBSCRIBER-IDENTITY-TC-MIB";
  prefix CISCO-SUBSCRIBER-IDENTITY-TC-MIB;

  import ietf-yang-smiv2 {
    prefix "smiv2";
  }

  organization
   "Cisco Systems, Inc.";

  contact
   "Cisco Systems
    Customer Service
    
    Postal: 170 W Tasman Drive
    San Jose, CA 95134
    
    Tel: +1 800 553-NETS
    
    E-mail: cs-snmp@cisco.com";

  description
   "This MIB module defines textual conventions describing
    subscriber session identities.  A subscriber session identity
    consists of data associated with a subscriber session serving as
    credentials used to determine authority, status, rights, or
    entitlement to privileges.";

  revision 2011-12-23 {
    description
     "The initial version of the MIB module.";
  }

  typedef SubSessionIdentity {
    type enumeration {
      enum "other" {
        value "1";
      }
      enum "ifIndex" {
        value "2";
      }
      enum "subscriberLabel" {
        value "3";
      }
      enum "macAddress" {
        value "4";
      }
      enum "nativeVrf" {
        value "5";
      }
      enum "nativeIpAddress" {
        value "6";
      }
      enum "domainVrf" {
        value "7";
      }
      enum "domainIpAddress" {
        value "8";
      }
      enum "pbhk" {
        value "9";
      }
      enum "remoteId" {
        value "10";
      }
      enum "circuitId" {
        value "11";
      }
      enum "nasPort" {
        value "12";
      }
      enum "domain" {
        value "13";
      }
      enum "username" {
        value "14";
      }
      enum "acctSessionId" {
        value "15";
      }
      enum "dnis" {
        value "16";
      }
      enum "media" {
        value "17";
      }
      enum "mlpNegotiated" {
        value "18";
      }
      enum "protocol" {
        value "19";
      }
      enum "serviceName" {
        value "20";
      }
      enum "dhcpClass" {
        value "21";
      }
      enum "tunnelName" {
        value "22";
      }
    }
    description
     "An enumerated integer-value describing a subscriber session
      identity:
      
          'other'
              The implementation of the MIB module using this textual
              convention does not recognize the subscriber session
              identity.
      
          'ifIndex'
              The ifIndex assigned to the interface representing the
              subscriber session.
      
          'subscriberLabel'
              The arbitrary integer-value assigned by the system
              to uniquely identify the subscriber session within the
              scope of the system.
      
          'macAddress'
              The subscriber's MAC address.
      
          'nativeVrf'
              The name of the VRF on which the subscriber session
              originates.
      
          'nativeIpAddress'
              The IP address assigned to the subscriber session on
      the
              customer-facing side of the system.
      
          'domainVrf'
              The name of the VRF to which the system transfers the
              subscriber session traffic.
      
          'domainIpAddress'
              The IP address assigned to the subscriber session on
      the
              service-facing side of the system.
      
          'pbhk'
              The Port-Bundle Host Key (PBHK) uniquely identifying
      the
              subscriber session.  A PBHK consists of a source IP
              address and a TCP port number.
      
          'remoteId'
              The name identifying the 'calling station', access
              multiplexor, or access switch providing access to the
              subscriber.
      
          'circuitId'
              The name identifying the circuit on the 'calling
              station', access multiplexor, or access switch that
              provides access to the subscriber.
      
          'nasPort'
              An octet string identifying the port on the Network
              Access Server (NAS) that provides access to the
              subscriber.
      
          'domain'
              The subscriber's domain name.
      
          'username'
              The subscriber's username.
      
          'acctSessionId'
              The subscriber's accounting session identifier.
      
          'dnis'
              The Dialed Number Identification Service (DNIS) number
              (or called-party number) dialed by the subscriber.
      
          'media'
              The type of media providing access to the subscriber.
      
          'mlpNegotiated'
              Indicates whether the subscriber session was
      established
              using multi-link PPP negotiation.
      
          'protocol'
              The type of protocol providing access to the
      subscriber.
      
          'dhcpClass'
              The name of the class matching the DHCP DISCOVER
      message
              received from the subscriber.
      
          'serviceName'
              The name identifying the service associated with the
              subscriber.
           'tunnelName'
               The name of the VPDN used to carry the subscriber
               session.";
  }

  typedef SubSessionIdentities {
    type bits {
      bit ifIndex {
        position "0";
      }
      bit subscriberLabel {
        position "1";
      }
      bit macAddress {
        position "2";
      }
      bit nativeVrf {
        position "3";
      }
      bit nativeIpAddress {
        position "4";
      }
      bit domainVrf {
        position "5";
      }
      bit domainIpAddress {
        position "6";
      }
      bit pbhk {
        position "7";
      }
      bit remoteId {
        position "8";
      }
      bit circuitId {
        position "9";
      }
      bit nasPort {
        position "10";
      }
      bit domain {
        position "11";
      }
      bit username {
        position "12";
      }
      bit acctSessionId {
        position "13";
      }
      bit dnis {
        position "14";
      }
      bit media {
        position "15";
      }
      bit mlpNegotiated {
        position "16";
      }
      bit protocol {
        position "17";
      }
      bit serviceName {
        position "18";
      }
      bit dhcpClass {
        position "19";
      }
      bit tunnelName {
        position "20";
      }
    }
    description
     "A bit string describing a set of subscriber session identities:
      
      'ifIndex'
          The ifIndex assigned to the interface representing the
          subscriber session.
      
      'subscriberLabel'
          The arbitrary integer-value assigned by the system
          to uniquely identify the subscriber session within the
          scope of the system.
      
      'macAddress'
          The subscriber's MAC address.
      
      'nativeVrf'
          The name of the VRF on which the subscriber session
          originates.
      
      'nativeIpAddress'
          The IP address assigned to the subscriber session on the
          customer-facing side of the system.
      
      'domainVrf'
          The name of the VRF to which the system transfers the
          subscriber session traffic.
      
      'domainIpAddress'
          The IP address assigned to the subscriber session on the
          service-facing side of the system.
      
      'pbhk'
          The Port-Bundle Host Key (PBHK) uniquely identifying the
          subscriber session.  A PBHK consists of a source IP
          address and a TCP port number.
      
      'remoteId'
          The name identifying the 'calling station' or access
          multiplexor providing access to the subscriber.
      
      'circuitId'
          The name identifying the circuit on the 'calling
          station', access multiplexor, or access switch that
          provides access to the subscriber.
      
      'nasPort'
          An octet string identifying the port on the Network
          Access Server (NAS) that provides access to the
          subscriber.
      
      'domain'
          The subscriber's domain name.
      
      'username'
          The subscriber's username.
      
      'dnis'
          The Dialed Number Identification Service (DNIS) number
          (or called-party number) dialed by the subscriber.
      
      'acctSessionId'
          The subscriber's accounting session identifier.
      
      'media'
          The type of media providing access to the subscriber.
      
      'mlpNegotiated'
          Indicates whether the subscriber session was established
          using multi-link PPP negotiation.
      
      'protocol'
          The type of protocol providing access to the subscriber.
      
      'serviceName'
          The name identifying the service associated with the
          subscriber.
      
      'dhcpClass'
          The name of the class matching the DHCP DISCOVER message
          received from the subscriber.
      
      'tunnelName'
          The name of the VPDN used to carry the subscriber
          session.";
  }

  typedef SubscriberLabel {
    type uint32 {
      range "0..4294967295";
    }
    description
     "A positive integer-value uniquely identifying a subscriber
      session within the scope of a system.
      
      The value '0' is not a valid value.  However, it serves as a
      convenient value when an instance of an object using this
      textual convention is not valid.";
    smiv2:display-hint "x";
  }

  typedef SubscriberVRF {
    type string;
    description
     "A string-value identifying a VRF associated with a subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberPbhk {
    type string;
    description
     "An octet string specifying a Port-Bundle Host Key (PBHK)
      identifying a subscriber.  The octet string has the following
      format:
      
          Octets  Field
          ------------------------------
          1-4     subscriber IP address
          5-6     TCP port number
      
      Observe that the subscriber IP address is always an IPv4
      address.
      
      The value '000000'H is not a valid value.  However, it serves as
      a convenient value when an instance of an object using this
      textual convention is not valid.";
    smiv2:display-hint "1x:";
  }

  typedef SubscriberRemoteId {
    type string;
    description
     "A string-value identifying the 'calling station', access
      multiplexor, or access switch providing access to a subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberCircuitId {
    type string;
    description
     "A string-value identifying the circuit on the 'calling
      station', access multiplexor, or access switch that provides
      access to the subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberNasPort {
    type string;
    description
     "An octet string identifying port on the Network Access Server
      (NAS) that provides access to the subscriber.
      
      The value '000000'H is not a valid value.  However, it serves as a
      convenient value when an instance of an object using this
      textual convention is not valid.";
    smiv2:display-hint "1x:";
  }

  typedef SubscriberDomain {
    type string;
    description
     "A string-value specifying the domain associated with a
      subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberUsername {
    type string;
    description
     "A string-value specifying the username identifying a
      subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberAcctSessionId {
    type uint32 {
      range "0..4294967295";
    }
    description
     "An positive, integer-value specifying the accounting session ID
      assigned to a subscriber.
      
      The value '0' is not a valid value.  However, it serves as a
      convenient value when an instance of an object using this
      textual convention is not valid.";
    smiv2:display-hint "x";
  }

  typedef SubscriberDnis {
    type string;
    description
     "A string-value specifying the Dialed Number Identification
      Service (DNIS) number (or called-party number) dialed by a
      subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberMediaType {
    type enumeration {
      enum "other" {
        value "1";
      }
      enum "async" {
        value "2";
      }
      enum "atm" {
        value "3";
      }
      enum "ethernet" {
        value "4";
      }
      enum "ip" {
        value "5";
      }
      enum "isdn" {
        value "6";
      }
      enum "mpls" {
        value "7";
      }
      enum "sync" {
        value "8";
      }
    }
    description
     "An enumerated integer-value describing the type of media
      providing access to the subscriber:
      
          'other'
              The implementation of the MIB module using this textual
              convention does not recognize the type of media
              providing access to the subscriber.
      
          'async'
              An asynchronous serial line provides access to the
              subscriber.
      
          'atm'
              An ATM network provides access to the subscriber.
      
          'ethernet'
              An Ethernet-based network provides access to the
              subscriber.
      
          'ip'
              An IP network provides access to the subscriber.
      
          'isdn'
              An ISDN line provides access to the subscriber.
      
          'mpls'
              An MPLS network provides access to the subscriber.
      
          'sync'
              A synchronous serial line provides access to the
              subscriber.
      
      The value 'other' cannot be written to an instance of an object.
      However, it serves as a convenient value when an instance of an
      object using this textual convention is not valid.";
  }

  typedef SubscriberProtocolType {
    type enumeration {
      enum "other" {
        value "1";
      }
      enum "atom" {
        value "2";
      }
      enum "ip" {
        value "3";
      }
      enum "psdn" {
        value "4";
      }
      enum "ppp" {
        value "5";
      }
      enum "vpdn" {
        value "6";
      }
    }
    description
     "An enumerated integer-value describing the type of protocol
      providing access to the subscriber:
      
          'other'
              The implementation of the MIB module using this textual
              convention does not recognize the type of protocol
              providing access to the subscriber.
      
          'atom'
              Any Transport over MPLS (AToM) provides access to the
              subscriber.
      
          'ip'
              The Internet Protocol (IP) provides access to the
              subscriber.
      
          'psdn'
              A Public Switched Data Network (PSDN) provides access to
              the subscriber.
      
          'ppp'
              The Point-to-Point Protocol (PPP) provides access to the
              subscriber.
      
          'vpdn'
              A Virtual Private Data Network (VPDN) provides access to
              the subscriber.
      
      The value 'other' cannot be written to an instance of an object.
      However, it serves as a convenient value when an instance of an
      object using this textual convention is not valid.";
  }

  typedef SubscriberDhcpClass {
    type string;
    description
     "A string-value specifying the name of the class matching the
      DHCP DISCOVER message received from the subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberTunnelName {
    type string;
    description
     "A string-value specifying the name of the VPDN used to carry
      a subscriber's session.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberLocationName {
    type string;
    description
     "A string-value specifying the location associated with a
      subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  typedef SubscriberServiceName {
    type string;
    description
     "A string-value specifying the subscriber service associated
      with a subscriber.
      
      The semantics of the string-value are the same those specified
      by the SnmpAdminString textual convention defined by the
      SNMP-FRAMEWORK-MIB (RFC-3411).
      
      The null string is not a valid value.  However, it serves as a
      convenient value when an instance of an object using this
      textual convention is not valid.";
    reference
     "D. Harrington, R. Resuhn, B. Wijnen, 'An Architecture for
      Describing Simple Network Management Protocol (SNMP)
      Management Frameworks', RFC-3411, December 2002.";
    smiv2:display-hint "255a";
  }

  smiv2:alias "ciscoSubscriberIdentityTcMIB" {
    smiv2:oid "1.3.6.1.4.1.9.9.782";
  }

}
