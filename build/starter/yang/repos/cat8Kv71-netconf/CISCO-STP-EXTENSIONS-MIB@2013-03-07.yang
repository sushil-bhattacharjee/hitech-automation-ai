/*
 * Generated by confdc --mib2yang-std
 * Source: mgmt/dmi/model/mib/src/patched/CISCO-STP-EXTENSIONS-MIB.mib
 */
/*
 * This YANG module has been generated by smidump 0.5.0:
 *
 *      smidump -f yang CISCO-STP-EXTENSIONS-MIB
 *
 * Do not edit. Edit the source file instead!
 */

module CISCO-STP-EXTENSIONS-MIB {

  namespace "urn:ietf:params:xml:ns:yang:smiv2:CISCO-STP-EXTENSIONS-MIB";
  prefix CISCO-STP-EXTENSIONS-MIB;

  import BRIDGE-MIB {
    prefix "bridge-mib";
  }

  import CISCO-VTP-MIB {
    prefix "cisco-vtp";
  }

  import SNMPv2-TC {
    prefix "snmpv2-tc";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-wbu@cisco.com";

  description
   "The MIB module for managing Cisco extensions to
    the 802.1D Spanning Tree Protocol (STP).";

  revision 2013-03-07 {
    description
     "Added one new value network(5) to stpxFastStartPortMode.";
  }

  revision 2005-12-20 {
    description
     "Added bit value rstp(5) to stpxSMSTPortStatus and
      dispute(4) to stpxRPVSTPortStatus.";
  }

  revision 2005-04-12 {
    description
     "Changed the description clauses of stpxMSTMaxHopCount
      and stpxMSTInstanceRemainingHopCount.
      Added StpxMSTConfigurationDigest textual convention.
      Deprecated stpxMSTGroup3 and added the following groups: 
          stpxRSTPTransmitHoldCountGroup,
          stpxSMSTPortMSTModeGroup, stpxSMSTMaxHopCountGroup,
          stpxSMSTConfigDigestGroup and stpxMSTGroup4.
      Added bit dispute(4) into the BITS syntax of
      stpxSMSTPortStatus.
      Deprecated stpxMIBCompliance11 and added 
      stpxMIBCompliance12.";
  }

  revision 2004-07-21 {
    description
     "Added stpxPathCostOperModeGroup
      and changed the decription of 
      stpxSpanningTreePathCostMode.";
  }

  revision 2004-04-08 {
    description
     "Added stpxSMSTInstanceCISTGroup.
      Added 3 new bit values into the BITS syntax
      of stpxNotificationEnable: 
      inconsistency(2), rootInconsistency(3), 
      and loopInconsistency(4).";
  }

  revision 2004-01-14 {
    description
     "Deprecated stpxMSTGroup2 and 
      stpxPreferredMSTInstancesGroup.
      Added stpxMSTGroup3, stpxSMSTGroup, 
      stpxSMSTInstanceGroup, stpxSMSTInstanceEditGroup,
      stpxSMSTPortStatusGroup, stpxSMSTPortHelloTimeGroup. 
      Added one new value master(7) to stpxMSTPortRoleValue
      and stpxRSTPPortRoleValue. Added 2 new unused bit 
      value into the BITS syntax of stpxRPVSTPortStatus.";
  }

  revision 2003-10-23 {
    description
     "Added stpxExtendedSysIDGroup,  
      stpxNotificationEnableGroup, and 
      stpxFastStartOperModeGroup.";
  }

  revision 2002-07-11 {
    description
     "Added Rapid Spanning Tree Protocol support.
      Added stpxUplinkFastOperEnabled and
      stpxBackboneFastOperEnabled objects.
      Replaced stpxMSTPortAdminLinkType, 
      stpxMSTPortOperLinkType, 
      stpxMSTPortProtocolMigration 
      with stpxRSTPPortAdminLinkType,
      stpxRSTPPortOperLinkType and 
      stpxRSTPPortProtocolMigration
      defined in stpxRSTPPortTable.
      Replaced stpxMSTPortRoleTable with
      stpxRSTPPortRoleTable. Added stpxRPVSTPortTable.";
  }

  revision 2001-12-06 {
    description
     "Added per port Bpdu Guard and Bpdu Filter 
      mode configuration support. Modified the
      description of stpxUplinkFastEnabled and
      stpxUplinkStationLearningGenRate for MST
      support. ";
  }

  revision 2001-09-14 {
    description
     "Added MST support, Loop Guard Global Default mode
      support and Fast Start Global Default mode support.
      Deprecated stpxFastStartPortEnable and 
      stpxLoopGuardConfigEnabled objects. Changed description
      of stpxUplinkFastEnabled, stpxUplinkFastTransitions,
      stpxUplinkStationLearningGenRate, 
      stpxUplinkStationLearningFrames objects for MST support.";
  }

  revision 2001-06-20 {
    description
     "Added BPDU Skewing feature support and modified
      the SYNTAX clause of stpxUplinkStationLearningGenRate.";
  }

  revision 2001-04-12 {
    description
     "Added PVST+ VLAN Configuration, MISTP to VLAN mapping,
      Loopguard, and Port Fast Start support.";
  }

  revision 2000-05-23 {
    description
     "Added Long Spanning Tree Path Cost Mode support.";
  }

  revision 2000-03-21 {
    description
     "Added Rootguard, 4k VLAN and MISTP support.";
  }

  revision 1997-11-10 {
    description
     "Additional objects to support SSTP.";
  }

  revision 1997-08-19 {
    description
     "Initial version of this MIB module.";
  }

  typedef StpxMSTConfigurationDigest {
    type string;
    description
     "Represents an MST configuration digest.";
    smiv2:display-hint "1x";
  }


  container CISCO-STP-EXTENSIONS-MIB {
    config false;

    container stpxUplinkFastObjects {
      smiv2:oid "1.3.6.1.4.1.9.9.82.1.1";

      leaf stpxUplinkFastEnabled {
        type boolean;
        description
         "An indication of whether the UplinkFast capability is
          administratively enabled on the device.
          
          If the platform does not support configuration of this
          object when the object value of stpxSpanningTreeType is 
          mst(4), then this object is not instantiated.";
        smiv2:max-access "read-write";
        smiv2:oid "1.3.6.1.4.1.9.9.82.1.1.1";
      }

      leaf stpxUplinkFastTransitions {
        type yang:counter32;
        units "transitions";
        description
         "The cumulative number of UplinkFast transitions (from
          the STP 'Blocking' state directly to the STP 'Forwarding'
          state).  All transitions are included in this counter,
          irrespective of the instance of the Spanning Tree 
          Protocol on which they occur.
          
          If the platform supports the stpxUplinkFastOperEnabled 
          object, then this object is not instantiated when the 
          object value of stpxUplinkFastOperEnabled is false(2).
          If the platform does not support the 
          stpxUplinkFastOperEnabled object, then this object is 
          not instantiated when the object value of 
          stpxSpanningTreeType is mst(4).";
        smiv2:max-access "read-only";
        smiv2:oid "1.3.6.1.4.1.9.9.82.1.1.2";
      }

      leaf stpxUplinkStationLearningGenRate {
        type int32 {
          range "0..32000";
        }
        units "frames";
        description
         "The maximum number of station-learning frames that this
          device will generate in each 100 milli-second period after
          a UplinkFast transition.  By configuring this object, the
          network administrator can limit the rate at which
          station-learning frames are generated.  
          
          If the platform does not support configuration of this
          object when the object value of stpxSpanningTreeType is
          mst(4), then this object is not instantiated.";
        smiv2:max-access "read-write";
        smiv2:oid "1.3.6.1.4.1.9.9.82.1.1.3";
      }

      leaf stpxUplinkStationLearningFrames {
        type yang:counter32;
        units "frames";
        description
         "The cumulative number of station-learning frames generated
          due to UplinkFast transitions.  All generated
          station-learning frames are included in this counter,
          irrespective of the instance of the Spanning Tree Protocol
          on which the UplinkFast transition occurred.
          
          If the platform supports the stpxUplinkFastOperEnabled 
          object, then this object is not instantiated when the 
          object value of stpxUplinkFastOperEnabled is false(2).
          If the platform does not support the 
          stpxUplinkFastOperEnabled object, then this object is 
          not instantiated when the object value of 
          stpxSpanningTreeType is mst(4).";
        smiv2:max-access "read-only";
        smiv2:oid "1.3.6.1.4.1.9.9.82.1.1.4";
      }

      leaf stpxUplinkFastOperEnabled {
        type boolean;
        description
         "An indication of whether the UplinkFast capability is 
          operationally enabled on the device.";
        smiv2:max-access "read-only";
        smiv2:oid "1.3.6.1.4.1.9.9.82.1.1.5";
      }
    }

    container stpxBackboneFastObjects {
      smiv2:oid "1.3.6.1.4.1.9.9.82.1.4";

      leaf stpxBackboneFastEnabled {
        type boolean;
        description
         "An indication of whether the BackboneFast capability is
          administratively enabled on the device.";
        smiv2:max-access "read-write";
        smiv2:oid "1.3.6.1.4.1.9.9.82.1.4.1";
      }

      leaf stpxBackboneFastInInferiorBPDUs {
        type yang:counter32;
        description
         "The number of inferior BPDUs received by the switch 
          since the stpxBackboneFastOperEnabled has
          become true(1). If the value of 
          stpxBackboneFastOperEnabled is false(2), then this 
          mib object will have a value of 0.";
        smiv2:max-access "read-only";
        smiv2:oid "1.3.6.1.4.1.9.9.82.1.4.2";
      }

      leaf stpxBackboneFastInRLQRequestPDUs {
        type yang:counter32;
        description
         "The number of Root Link Query request PDUs received by the
          switch since the stpxBackboneFastOperEnabled has become
          true(1). If the value of stpxBackboneFastOperEnabled is
          false(2), then this mib object will have a value of 0.";
        smiv2:max-access "read-only";
        smiv2:oid "1.3.6.1.4.1.9.9.82.1.4.3";
      }

      leaf stpxBackboneFastInRLQResponsePDUs {
        type yang:counter32;
        description
         "The number of Root Link Query response PDUs received by the
          switch since the stpxBackboneFastOperEnabled has become
          true(1). If the value of stpxBackboneFastOperEnabled is
          false(2), then this mib object will have a value of 0.";
        smiv2:max-access "read-only";
        smiv2:oid "1.3.6.1.4.1.9.9.82.1.4.4";
      }

      leaf stpxBackboneFastOutRLQRequestPDUs {
        type yang:counter32;
        description
         "The number of Root Link Query request PDUs transmitted by
          the switch since the stpxBackboneFastOperEnabled has become
          true(1). If the value of stpxBackboneFastOperEnabled is
          false(2), then this mib object will have a value of 0.";
        smiv2:max-access "read-only";
        smiv2:oid "1.3.6.1.4.1.9.9.82.1.4.5";
      }

      leaf stpxBackboneFastOutRLQResponsePDUs {
        type yang:counter32;
        description
         "The number of Root Link Query response PDUs transmitted by
          the switch since the stpxBackboneFastOperEnabled has become
          true(1). If the value of stpxBackboneFastOperEnabled is
          false(2), then this mib object will have a value of 0.";
        smiv2:max-access "read-only";
        smiv2:oid "1.3.6.1.4.1.9.9.82.1.4.6";
      }

      leaf stpxBackboneFastOperEnabled {
        type boolean;
        description
         "An indication of whether the BackboneFast capability is
          operationally enabled on the device.";
        smiv2:max-access "read-only";
        smiv2:oid "1.3.6.1.4.1.9.9.82.1.4.7";
      }
    }

    container stpxSpanningTreeObjects {
      smiv2:oid "1.3.6.1.4.1.9.9.82.1.6";

      leaf stpxSpanningTreeType {
        type enumeration {
          enum "pvstPlus" {
            value "1";
          }
          enum "mistp" {
            value "2";
          }
          enum "mistpPvstPlus" {
            value "3";
          }
          enum "mst" {
            value "4";
          }
          enum "rapidPvstPlus" {
            value "5";
          }
        }
        description
         "The actual mode of spanning tree protocol runs
          on the  device. It can be one of the following:
          
          pvstPlus -- PVST+ (Per VLAN Spanning Tree+ Protocol).
          
          mistp -- MISTP (Multi Instance Spanning Tree Protocol).
          
          mistpPvstPlus --  MISTP with the tunneling scheme
                               enabled for PVST+.
          
          mst -- IEEE 802.1s Multiple Spanning Tree (MST)
                 with IEEE 802.1w Rapid Spanning Tree Protocol
                 (RSTP).
          
          rapidPvstPlus -- IEEE 802.1w Rapid Spanning Tree 
                  Protocol (RSTP) for all vlans in PVST+.
          
          When the value of this MIB object gets changed, the 
          network connectivity would be affected and the 
          connectivity to this device would also be lost 
          temporarily.";
        smiv2:defval "pvstPlus";
        smiv2:max-access "read-write";
        smiv2:oid "1.3.6.1.4.1.9.9.82.1.6.1";
      }

      leaf stpxSpanningTreePathCostMode {
        type enumeration {
          enum "short" {
            value "1";
          }
          enum "long" {
            value "2";
          }
        }
        description
         "Indicates the administrative  spanning tree path cost mode 
          configured on device.";
        smiv2:defval "short";
        smiv2:max-access "read-write";
        smiv2:oid "1.3.6.1.4.1.9.9.82.1.6.2";
      }

      leaf stpxExtendedSysIDAdminEnabled {
        type boolean;
        description
         "Indicates whether Extended System ID feature 
          is administratively enabled on the device or not.";
        reference
         "IEEE 802.1t.";
        smiv2:max-access "read-write";
        smiv2:oid "1.3.6.1.4.1.9.9.82.1.6.4";
      }

      leaf stpxExtendedSysIDOperEnabled {
        type boolean;
        description
         "Indicates whether Extended System ID feature 
          is operationaly enabled on the device or not.
          
          If the value of this object is true(1), then
          the accepted values for dot1dStpPriority
          in BRIDGE-MIB should be multiples of 4096 plus
          bridge instance ID, such as VlanIndex. Changing
          this object value might cause the values of
          dot1dBaseBridgeAddress and dot1dStpPriority
          in BRIDGE-MIB to be changed also.";
        reference
         "IEEE 802.1t.";
        smiv2:max-access "read-only";
        smiv2:oid "1.3.6.1.4.1.9.9.82.1.6.5";
      }

      leaf stpxNotificationEnable {
        type bits {
          bit newRoot {
            position "0";
          }
          bit topologyChange {
            position "1";
          }
          bit inconsistency {
            position "2";
          }
          bit rootInconsistency {
            position "3";
          }
          bit loopInconsistency {
            position "4";
          }
        }
        description
         "Indicates whether a specified notification is enabled or not.
          If a bit corresponding to a notification is set to 1, then 
          the specified notification can be generated.
          
          newRoot -- the newRoot notification as defined in BRIDGE-MIB.
          
          topologyChange -- the topologyChange notification as
                            defined in BRIDGE-MIB.
          
          inconsistency -- the stpxInconsistencyUpdate notification.
          
          rootInconsistency -- the stpxRootInconsistencyUpdate 
                               notification.
          
          loopInconsistency -- the stpxLoopInconsistencyUpdate 
                               notification.";
        smiv2:max-access "read-write";
        smiv2:oid "1.3.6.1.4.1.9.9.82.1.6.6";
      }

      leaf stpxSpanningTreePathCostOperMode {
        type enumeration {
          enum "short" {
            value "1";
          }
          enum "long" {
            value "2";
          }
        }
        description
         "Indicate the operational spanning tree path cost mode
          on device. This mode applies to all instances of the Spanning
          Tree protocol running on the device. 
          
          When the value of this MIB object gets changed, the path cost
          of all ports will be reassigned to the default path cost
          values based on the new spanning tree path cost mode and the
          ports' speed.
          
          When the value of this MIB object is long(2),
          the stpxLongStpPortPathCost MIB object must be used in order
          to retrieve/configure the spanning tree port path cost as a
          32 bits value. The set operation on dot1dStpPortPathCost in
          BRIDGE-MIB will be rejected. While retrieving the value of
          dot1dStpPortPathCost, the maximum value of 65535 will be
          returned if the value of stpxLongStpPortPathCost for the same
          instance exceeds 65535.
          
          When the value of this MIB object is short(1),
          the dot1dStpPortPathCost in BRIDGE-MIB must be used.";
        smiv2:max-access "read-only";
        smiv2:oid "1.3.6.1.4.1.9.9.82.1.6.7";
      }
    }

    container stpxMISTPObjects {
      smiv2:oid "1.3.6.1.4.1.9.9.82.1.7";

      leaf stpxMISTPInstanceNumber {
        type int32 {
          range "1..256";
        }
        description
         "The number of MISTP instances, that are supported by the device 
          when the value of stpxSpanningTreeType is either mistp(2)
          or mistpPvstPlus(3).";
        smiv2:max-access "read-only";
        smiv2:oid "1.3.6.1.4.1.9.9.82.1.7.1";
      }
    }

    container stpxLoopGuardObjects {
      smiv2:oid "1.3.6.1.4.1.9.9.82.1.8";

      leaf stpxLoopGuardGlobalDefaultMode {
        type enumeration {
          enum "enable" {
            value "1";
          }
          enum "disable" {
            value "2";
          }
        }
        description
         "Indicates the global default config mode of LoopGuard 
          feature on the device.";
        smiv2:max-access "read-write";
        smiv2:oid "1.3.6.1.4.1.9.9.82.1.8.3";
      }
    }

    container stpxFastStartObjects {
      smiv2:oid "1.3.6.1.4.1.9.9.82.1.9";

      leaf stpxFastStartBpduGuardEnable {
        type boolean;
        description
         "Indicates the global default mode of the Bpdu
          Guard feature on the device.
          
          On platforms that does not support per port 
          Bpdu Guard configuration as indicated by
          the object stpxFastStartPortBpduGuardMode,
          if  the value of this object is set to true(1), 
          and the Fast Start Feature is operationally 
          enabled on a port, then that port will be 
          immediately disabled when the system receives
          a BPDU from that port.";
        smiv2:defval "false";
        smiv2:max-access "read-write";
        smiv2:oid "1.3.6.1.4.1.9.9.82.1.9.1";
      }

      leaf stpxFastStartBpduFilterEnable {
        type boolean;
        description
         "Indicates the global default mode of the Bpdu 
          Filter feature on the device.
          
          On platforms that does not support per port 
          Bpdu Filter configuration as indicated by
          the object stpxFastStartPortBpduFilterMode,
          if  the value of this object is set to true(1), 
          and the Fast Start Feature is operationally 
          enabled on a port, then no BPDUs will be 
          transmitted on this port.";
        smiv2:defval "false";
        smiv2:max-access "read-write";
        smiv2:oid "1.3.6.1.4.1.9.9.82.1.9.2";
      }

      leaf stpxFastStartGlobalDefaultMode {
        type enumeration {
          enum "enable" {
            value "1";
          }
          enum "disable" {
            value "2";
          }
        }
        description
         "Indicates the global default mode of the Fast 
          Start feature on the device.";
        smiv2:defval "disable";
        smiv2:max-access "read-write";
        smiv2:oid "1.3.6.1.4.1.9.9.82.1.9.4";
      }
    }

    container stpxBpduSkewingObjects {
      smiv2:oid "1.3.6.1.4.1.9.9.82.1.10";

      leaf stpxBpduSkewingDetectionEnable {
        type boolean;
        description
         "Indicates whether BPDU skewing detection feature
          is enabled or not on the system. If this object has
          the value of true(1), then the system will detect
          whether BPDUs received by any port on any Spanning 
          Tree instance are processed at an interval longer
          than the object value of dot1dStpHelloTime in the
          BIRDGE-MIB of the Spanning Tree instance.";
        smiv2:defval "false";
        smiv2:max-access "read-write";
        smiv2:oid "1.3.6.1.4.1.9.9.82.1.10.1";
      }
    }

    container stpxMSTObjects {
      smiv2:oid "1.3.6.1.4.1.9.9.82.1.11";

      leaf stpxMSTMaxInstanceNumber {
        type int32 {
          range "1..256";
        }
        status deprecated;
        description
         "The maximum MST (Multiple Spanning Tree) instance id, 
          that can be supported by the device for Cisco proprietary
          implementation of the MST Protocol.
          
          This object is deprecated and replaced by 
          stpxSMSTMaxInstanceID.";
        smiv2:max-access "read-only";
        smiv2:oid "1.3.6.1.4.1.9.9.82.1.11.1";
      }

      leaf stpxMSTRegionName {
        type snmpv2-tc:DisplayString {
          length "0..32";
        }
        description
         "The operational MST region name.";
        smiv2:max-access "read-only";
        smiv2:oid "1.3.6.1.4.1.9.9.82.1.11.2";
      }

      leaf stpxMSTRegionRevision {
        type int32 {
          range "0..65535";
        }
        status deprecated;
        description
         "The operational MST region version.
          
          This object is deprecated and replaced by 
          stpxSMSTRegionRevision.";
        smiv2:max-access "read-only";
        smiv2:oid "1.3.6.1.4.1.9.9.82.1.11.3";
      }

      leaf stpxMSTRegionEditBufferStatus {
        type enumeration {
          enum "released" {
            value "1";
          }
          enum "acquiredBySnmp" {
            value "2";
          }
          enum "acquiredByNonSnmp" {
            value "3";
          }
        }
        description
         "Indicates the current ownership status of the unique 
          Region Config Edit Buffer. 
          
          released -- the Edit Buffer can be acquired by any of 
                      the SNMP management stations. 
          
          acquiredBySnmp -- the Edit Buffer is acquired by
                      any of the SNMP management stations. 
          
          acquiredByNonSnmp -- the Edit Buffer is acquired by the 
                      non-SNMP users managing the device.";
        smiv2:max-access "read-only";
        smiv2:oid "1.3.6.1.4.1.9.9.82.1.11.5";
      }

      leaf stpxMSTRegionEditBufferOperation {
        type enumeration {
          enum "other" {
            value "1";
          }
          enum "acquire" {
            value "2";
          }
          enum "releaseWithForce" {
            value "3";
          }
          enum "commit" {
            value "4";
          }
          enum "rollBack" {
            value "5";
          }
        }
        description
         "Indicates the operation that is performed on the Region 
          Config Edit Buffer.
          
          other --   none of the following operations.  
          
          acquire -- acquire the Edit Buffer. This operation can 
                     only be performed when the object 
                     stpxMSTRegionEditBufferStatus has the value of
                     released(1). After the successful operation of 
                     this action, the stpxMSTRegionEditBufferStatus
                     will be changed to acquiredBySnmp(2). 
                      
          releaseWithForce -- release the Edit Buffer acquired by
                     non-SNMP users with force and discard the changes
                     in the Edit Buffer. This operation can only be 
                     performed when the object 
                     stpxMSTRegionEditBufferStatus has the value of 
                     acquiredByNonSnmp(2).
          
          commit --  commit the changes in the Edit Buffer
                     and release the Edit Buffer. The successful 
                     operation of this action will make the changes
                     in the Edit Buffer effective on the device.
                     This operation can only be performed when the 
                     object stpxMSTRegionEditBufferStatus has the 
                     value of acquiredBySnmp(3).
           
          rollBack -- discard the changes in the Edit Buffer
                     and release the Edit Buffer. This operation can 
                     only be performed when the object 
                     stpxMSTRegionEditBufferStatus has the value 
                     of acquiredBySnmp(3).
          
          This object always returns other(1) when it is read.";
        smiv2:max-access "read-write";
        smiv2:oid "1.3.6.1.4.1.9.9.82.1.11.6";
      }

      leaf stpxMSTRegionEditName {
        type snmpv2-tc:DisplayString {
          length "0..32";
        }
        description
         "The MST region name in the Edit Buffer. 
          
          This object is only instantiated when the 
          stpxMSTRegionEditBufferStatus has the value of 
          acquiredBySnmp(2).";
        smiv2:max-access "read-write";
        smiv2:oid "1.3.6.1.4.1.9.9.82.1.11.7";
      }

      leaf stpxMSTRegionEditRevision {
        type int32 {
          range "1..65535";
        }
        status deprecated;
        description
         "The MST region version in the Edit Buffer. This object is
          only instantiated when the stpxMSTRegionEditBufferStatus 
          has the value of acquiredBySnmp(2).
          
          This object is deprecated and replaced by
          stpxSMSTRegionEditRevision.";
        smiv2:max-access "read-write";
        smiv2:oid "1.3.6.1.4.1.9.9.82.1.11.8";
      }

      leaf stpxMSTMaxHopCount {
        type int32 {
          range "1..40";
        }
        status deprecated;
        description
         "The maximum number of hops for the MST region. 
          
          This object will take on value of 40 if the object value
          of stpxSMSTMaxHopCount is greater than 40.
          
          This object is deprecated and replaced by
          stpxSMSTMaxHopCount.";
        smiv2:defval "20";
        smiv2:max-access "read-write";
        smiv2:oid "1.3.6.1.4.1.9.9.82.1.11.13";
      }
    }

    container stpxRSTPObjects {
      smiv2:oid "1.3.6.1.4.1.9.9.82.1.12";

      leaf stpxRSTPTransmitHoldCount {
        type uint32;
        description
         "The Transmit Hold Count.";
        smiv2:max-access "read-write";
        smiv2:oid "1.3.6.1.4.1.9.9.82.1.12.3";
      }
    }

    container stpxSMSTObjects {
      smiv2:oid "1.3.6.1.4.1.9.9.82.1.14";

      leaf stpxSMSTMaxInstances {
        type uint32;
        description
         "The maximum number of MST instances that can be 
          supported by the device for IEEE MST.";
        smiv2:max-access "read-only";
        smiv2:oid "1.3.6.1.4.1.9.9.82.1.14.1";
      }

      leaf stpxSMSTMaxInstanceID {
        type uint32;
        description
         "The maximum MST instance ID that can be supported 
          by the device for IEEE MST.";
        smiv2:max-access "read-only";
        smiv2:oid "1.3.6.1.4.1.9.9.82.1.14.2";
      }

      leaf stpxSMSTRegionRevision {
        type uint32;
        description
         "The operational region version for IEEE MST.";
        smiv2:max-access "read-only";
        smiv2:oid "1.3.6.1.4.1.9.9.82.1.14.3";
      }

      leaf stpxSMSTRegionEditRevision {
        type uint32;
        description
         "The MST region version in the Edit Buffer for IEEE 
          MST.
          
          This object is only instantiated when the 
          stpxMSTRegionEditBufferStatus has the value of 
          acquiredBySnmp(2).";
        smiv2:max-access "read-write";
        smiv2:oid "1.3.6.1.4.1.9.9.82.1.14.4";
      }

      leaf stpxSMSTMaxHopCount {
        type uint32;
        description
         "The maximum number of hops for the IEEE MST region.";
        smiv2:max-access "read-write";
        smiv2:oid "1.3.6.1.4.1.9.9.82.1.14.8";
      }

      leaf stpxSMSTConfigDigest {
        type CISCO-STP-EXTENSIONS-MIB:StpxMSTConfigurationDigest;
        description
         "The IEEE MST region configuration digest.";
        reference
         "IEEE 802.1Q-2003 Section 13.7.";
        smiv2:max-access "read-only";
        smiv2:oid "1.3.6.1.4.1.9.9.82.1.14.9";
      }

      leaf stpxSMSTConfigPreStandardDigest {
        type CISCO-STP-EXTENSIONS-MIB:StpxMSTConfigurationDigest;
        description
         "The pre-standard MST region configuration digest.";
        smiv2:max-access "read-only";
        smiv2:oid "1.3.6.1.4.1.9.9.82.1.14.10";
      }
    }

    container stpxPVSTVlanTable {
      description
       "A list of Virtual LAN entries containing
        information for Spanning Tree PVST+ protocol. 
        An entry will exist for each VLAN existing on 
        the device.";
      smiv2:oid "1.3.6.1.4.1.9.9.82.1.2.2";

      list stpxPVSTVlanEntry {
        key "stpxPVSTVlanIndex";
        description
         "An entry containing Spanning Tree PVST+ Protocol 
          information for a particular Virtual LAN.";
        smiv2:oid "1.3.6.1.4.1.9.9.82.1.2.2.1";

        leaf stpxPVSTVlanIndex {
          type cisco-vtp:VlanIndex;
          description
           "An index value that uniquely identifies the
            Virtual LAN associated with this information.";
          smiv2:max-access "not-accessible";
          smiv2:oid "1.3.6.1.4.1.9.9.82.1.2.2.1.1";
        }

        leaf stpxPVSTVlanEnable {
          type enumeration {
            enum "enabled" {
              value "1";
            }
            enum "disabled" {
              value "2";
            }
            enum "notApplicable" {
              value "3";
            }
          }
          description
           "Indicates whether Spanning Tree PVST+  
            Protocol is enabled for this Virtual LAN. If 
            Spanning Tree PVST+ Protocol is not supported 
            on this VLAN, then notApplicable(3) will be 
            returned while retrieving the object value for 
            this VLAN.
            
            If the device only supports a single global
            Spanning Tree PVST+ Protocol enable/disable 
            for all the existing VLANs, then the object 
            value assigned to this VLAN will be applied
            to the object values of all the instances
            in this table which do not have the value
            of notApplicable(3).
            
            If the value of stpxSpanningTreeType is neither 
            pvstPlus(1) nor rapidPvstPlus(5), then the value 
            of stpxPVSTVlanEnable for this VLAN can not be 
            changed.";
          smiv2:defval "enabled";
          smiv2:max-access "read-write";
          smiv2:oid "1.3.6.1.4.1.9.9.82.1.2.2.1.2";
        }
      }
    }

    container stpxInconsistencyTable {
      description
       "A table containing a list of the ports for which
        a particular VLAN's Spanning Tree has been found to
        have an inconsistency.  Two types of inconsistency
        are discovered: 1) an inconsistency where two different
        port types have been plugged together; and 2) an
        inconsistency where different switches have different
        PVIDs for the same link.";
      smiv2:oid "1.3.6.1.4.1.9.9.82.1.3.1";

      list stpxInconsistencyEntry {
        key "stpxVlanIndex stpxPortIndex";
        description
         "A VLAN on a particular port for which a Spanning Tree
          inconsistency is currently in effect.";
        smiv2:oid "1.3.6.1.4.1.9.9.82.1.3.1.1";

        leaf stpxVlanIndex {
          type cisco-vtp:VlanIndex;
          description
           "The VLAN id of the VLAN.";
          smiv2:max-access "not-accessible";
          smiv2:oid "1.3.6.1.4.1.9.9.82.1.3.1.1.1";
        }

        leaf stpxPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.3.1.1.2";
        }

        leaf stpxInconsistentState {
          type bits {
            bit typeInconsistent {
              position "0";
            }
            bit pvidInconsistent {
              position "1";
            }
          }
          description
           "The types of inconsistency which have been discovered on
            this port for this VLAN's Spanning Tree.
            
            When this object exists, the value of the corresponding
            instance of the Bridge MIB's dot1dStpPortState object will
            be 'broken(6)'.";
          reference
           "dot1dStpPortState is defined in RFC-1493.";
          smiv2:max-access "read-only";
          smiv2:oid "1.3.6.1.4.1.9.9.82.1.3.1.1.3";
        }
      }
    }

    container stpxRootGuardConfigTable {
      description
       "A table containing a list of the bridge ports for which
        Spanning Tree RootGuard capability can be configured.";
      smiv2:oid "1.3.6.1.4.1.9.9.82.1.5.1";

      list stpxRootGuardConfigEntry {
        key "stpxRootGuardConfigPortIndex";
        description
         "A bridge port for which Spanning Tree RootGuard
          capability can be configured.";
        smiv2:oid "1.3.6.1.4.1.9.9.82.1.5.1.1";

        leaf stpxRootGuardConfigPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.5.1.1.1";
        }

        leaf stpxRootGuardConfigEnabled {
          type boolean;
          description
           "An indication of whether the RootGuard capability is 
            enabled on this port or not. This configuration will be
            applied to all Spanning Tree instances in which this port 
            exists.";
          smiv2:defval "false";
          smiv2:max-access "read-write";
          smiv2:oid "1.3.6.1.4.1.9.9.82.1.5.1.1.2";
        }
      }
    }

    container stpxRootInconsistencyTable {
      description
       "A table containing a list of the bridge ports for which
        a particular Spanning Tree instance has been found 
        to have an root-inconsistency. The agent creates a new 
        entry in this table whenever it detects a new 
        root-inconsistency, and deletes entries 
        when/soon after the inconsistency is no longer present.";
      smiv2:oid "1.3.6.1.4.1.9.9.82.1.5.2";

      list stpxRootInconsistencyEntry {
        key "stpxRootInconsistencyIndex stpxRootInconsistencyPortIndex";
        description
         "A Spanning Tree instance on a particular port for 
          which a Spanning Tree root-inconsistency is currently 
          in effect.";
        smiv2:oid "1.3.6.1.4.1.9.9.82.1.5.2.1";

        leaf stpxRootInconsistencyIndex {
          type int32 {
            range "0..65535";
          }
          description
           "The Spanning Tree instance id, such as the VLAN id
            of the VLAN if the object value of stpxSpanningTreeType
            is pvstPlus(1) or rapidPvstPlus(5).";
          smiv2:max-access "not-accessible";
          smiv2:oid "1.3.6.1.4.1.9.9.82.1.5.2.1.1";
        }

        leaf stpxRootInconsistencyPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.5.2.1.2";
        }

        leaf stpxRootInconsistencyState {
          type boolean;
          description
           "Indicates whether the port on a particular Spanning 
            Tree instance is currently in root-inconsistent 
            state or not.";
          smiv2:max-access "read-only";
          smiv2:oid "1.3.6.1.4.1.9.9.82.1.5.2.1.3";
        }
      }
    }

    container stpxMISTPInstanceTable {
      description
       "This table contains one entry for each instance of MISTP and 
        it contains stpxMISTPInstanceNumber entries, numbered from 1
        to stpxMISTPInstanceNumber.
        
        This table is only instantiated when the value of 
        stpxSpanningTreeType is mistp(2) or mistpPvstPlus(3).";
      smiv2:oid "1.3.6.1.4.1.9.9.82.1.7.2";

      list stpxMISTPInstanceEntry {
        key "stpxMISTPInstanceIndex";
        description
         "A conceptual row containing the status of the MISTP 
          instance.";
        smiv2:oid "1.3.6.1.4.1.9.9.82.1.7.2.1";

        leaf stpxMISTPInstanceIndex {
          type int32 {
            range "1..256";
          }
          description
           "An arbitrary integer within the range from 1 to the value of
            stpxMISTPInstanceNumber that uniquely identifies an instance.";
          smiv2:max-access "not-accessible";
          smiv2:oid "1.3.6.1.4.1.9.9.82.1.7.2.1.1";
        }

        leaf stpxMISTPInstanceEnable {
          type boolean;
          description
           "This object indicates whether the MISTP protocol is currently
            enabled on the MISTP instance.
            
            If this object is set to
               'true'    - the MISTP protocol will run on this instance.
                          
               'false'   - the MISTP protocol will stop running on this 
                           instance.";
          smiv2:defval "true";
          smiv2:max-access "read-write";
          smiv2:oid "1.3.6.1.4.1.9.9.82.1.7.2.1.2";
        }

        leaf stpxMISTPInstanceVlansMapped {
          type binary {
            length "0..128";
          }
          description
           "A string of octets containing one bit per VLAN. The
            first octet corresponds to VLANs with VlanIndex values
            of 0 through 7; the second octet to VLANs 8 through
            15; etc.  The most significant bit of each octet
            corresponds to the lowest value VlanIndex in that octet.
            
            For each VLAN, if it is mapped to this MISTP instance,
            then the bit corresponding to that VLAN is set to '1'.";
          smiv2:max-access "read-only";
          smiv2:oid "1.3.6.1.4.1.9.9.82.1.7.2.1.3";
        }

        leaf stpxMISTPInstanceVlansMapped2k {
          type binary {
            length "0..128";
          }
          description
           "A string of octets containing one bit per VLAN for
            VLANS with VlanIndex values of 1024 through 2047. The
            first octet corresponds to VLANs with VlanIndex values
            of 1024 through 1031; the second octet to VLANs 1032
            through 1039; etc.  The most significant bit of each
            octet corresponds to the lowest value VlanIndex in that
            octet.
            
            For each VLAN, if it is mapped to this MISTP instance,
            then the bit corresponding to that VLAN is set to '1'.
            
            This object is only instantiated on devices with 
            support for VlanIndex up to 4095.";
          smiv2:max-access "read-only";
          smiv2:oid "1.3.6.1.4.1.9.9.82.1.7.2.1.4";
        }

        leaf stpxMISTPInstanceVlansMapped3k {
          type binary {
            length "0..128";
          }
          description
           "A string of octets containing one bit per VLAN for
            VLANS with VlanIndex values of 2048 through 3071. The
            first octet corresponds to VLANs with VlanIndex values
            of 2048 through 2055; the second octet to VLANs 2056
            through 2063; etc.  The most significant bit of each
            octet corresponds to the lowest value VlanIndex in that
            octet.
            
            For each VLAN, if it is mapped to this MISTP instance,
            then the bit corresponding to that VLAN is set to '1'.
            
            This object is only instantiated on devices with 
            support for VlanIndex up to 4095.";
          smiv2:max-access "read-only";
          smiv2:oid "1.3.6.1.4.1.9.9.82.1.7.2.1.5";
        }

        leaf stpxMISTPInstanceVlansMapped4k {
          type binary {
            length "0..128";
          }
          description
           "A string of octets containing one bit per VLAN for
            VLANS with VlanIndex values of 3072 through 4095. The
            first octet corresponds to VLANs with VlanIndex values
            of 3072 through 3079; the second octet to VLANs 3080
            through 3087; etc.  The most significant bit of each
            octet corresponds to the lowest value VlanIndex in that
            octet.
            
            For each VLAN, if it is mapped to this MISTP instance,
            then the bit corresponding to that VLAN is set to '1'.
            
            This object is only instantiated on devices with 
            support for VlanIndex up to 4095.";
          smiv2:max-access "read-only";
          smiv2:oid "1.3.6.1.4.1.9.9.82.1.7.2.1.6";
        }
      }
    }

    container stpxLoopGuardConfigTable {
      description
       "A table containing a list of the bridge ports for which
        Spanning Tree LoopGuard capability can be configured.";
      smiv2:oid "1.3.6.1.4.1.9.9.82.1.8.1";

      list stpxLoopGuardConfigEntry {
        key "stpxLoopGuardConfigPortIndex";
        description
         "A bridge port for which Spanning Tree LoopGuard 
          capability can be configured.";
        smiv2:oid "1.3.6.1.4.1.9.9.82.1.8.1.1";

        leaf stpxLoopGuardConfigPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.8.1.1.1";
        }

        leaf stpxLoopGuardConfigEnabled {
          type boolean;
          status deprecated;
          description
           "An indication of whether the LoopGuard capability is 
            enabled on this port or not. This configuration will be
            applied to all the Spanning Tree instances in which this 
            port exists.
            
            In order to support additional Loop Guard config mode
            (default) as defined in stpxLoopGuardConfigMode other 
            than enable (true(1)) or disable (false(2)) as defined 
            in this object, stpxLoopGuardConfigMode object needs to 
            be used.
            
            When the stpxLoopGuardConfigMode object has the value of
            enable(1), the value of stpxLoopGuardConfigEnabled for 
            the same instance will be true(1). When the 
            stpxLoopGuardConfigMode object has the value of disable(2), 
            the value of stpxLoopGuardConfigEnabled for the same 
            instance will be false(2). When the stpxLoopGuardConfigMode 
            object has the value of default(3), the value of 
            stpxLoopGuardConfigEnabled for the same instance will 
            depend on the object value of 
            stpxLoopGuardGlobalDefaultMode.";
          smiv2:defval "false";
          smiv2:max-access "read-write";
          smiv2:oid "1.3.6.1.4.1.9.9.82.1.8.1.1.2";
        }

        leaf stpxLoopGuardConfigMode {
          type enumeration {
            enum "enable" {
              value "1";
            }
            enum "disable" {
              value "2";
            }
            enum "default" {
              value "3";
            }
          }
          description
           "Indicates the mode of Loop Guard Feature on this 
            port. This configuration will be applied to all 
            the Spanning Tree instances in which this port 
            exists.
            
            enable -- the Loop Guard feature is enabled on this 
                      port. 
            
            disable -- the Loop Guard feature is disabled on this 
                      port.  
            
            default -- whether the Loop Guard feature is enabled
                       or not on this port depends on the object 
                       value of stpxLoopGuardGlobalDefaultMode.";
          smiv2:max-access "read-write";
          smiv2:oid "1.3.6.1.4.1.9.9.82.1.8.1.1.3";
        }
      }
    }

    container stpxLoopInconsistencyTable {
      description
       "A table containing a list of the bridge ports for which
        a particular Spanning Tree instance has been found
        to have a loop-inconsistency. The agent creates a new
        entry in this table whenever it detects a new
        loop-inconsistency, and deletes entries
        when/soon after the inconsistency is no longer present.";
      smiv2:oid "1.3.6.1.4.1.9.9.82.1.8.2";

      list stpxLoopInconsistencyEntry {
        key "stpxLoopInconsistencyIndex stpxLoopInconsistencyPortIndex";
        description
         "A Spanning Tree instance on a particular port for
          which a Spanning Tree loop-inconsistency is currently
          in effect.";
        smiv2:oid "1.3.6.1.4.1.9.9.82.1.8.2.1";

        leaf stpxLoopInconsistencyIndex {
          type int32 {
            range "0..65535";
          }
          description
           "The Spanning Tree instance id, such as the VLAN id
            of the VLAN if the object value of stpxSpanningTreeType
            is pvstPlus(1) or rapidPvstPlus(5).";
          smiv2:max-access "not-accessible";
          smiv2:oid "1.3.6.1.4.1.9.9.82.1.8.2.1.1";
        }

        leaf stpxLoopInconsistencyPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.8.2.1.2";
        }

        leaf stpxLoopInconsistencyState {
          type boolean;
          description
           "Indicates whether the port on a particular Spanning 
            Tree instance is currently in loop-inconsistent 
            state or not.";
          smiv2:max-access "read-only";
          smiv2:oid "1.3.6.1.4.1.9.9.82.1.8.2.1.3";
        }
      }
    }

    container stpxFastStartPortTable {
      description
       "A table containing a list of the bridge ports for
        which Spanning Tree Port Fast Start can be
        configured.";
      smiv2:oid "1.3.6.1.4.1.9.9.82.1.9.3";

      list stpxFastStartPortEntry {
        key "stpxFastStartPortIndex";
        description
         "A bridge port for which Spanning Tree Port Fast
          Start can be configured.";
        smiv2:oid "1.3.6.1.4.1.9.9.82.1.9.3.1";

        leaf stpxFastStartPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.9.3.1.1";
        }

        leaf stpxFastStartPortEnable {
          type boolean;
          status deprecated;
          description
           "Indicates whether the port is operating in spantree
            fast start mode.  A port with fast start enabled is
            immediately put in spanning tree forwarding state when
            that port is detected by the Spanning Tree, rather 
            than starting in blocking state which is the normal 
            operation.
            
            In order to support additional Fast Start enable mode
            (enableForTrunk and default) as defined in
            stpxFastStartPortMode other than enable (true(1))
            or disable (false(2)) as defined in this object,
            stpxFastStartPortMode object needs to be used.
            
            When the stpxFastStartPortMode has the value of
            enable(1) or enableForTrunk(3), the value of
            stpxFastStartPortEnable for the same instance
            will be true(1). When the stpxFastStartPortMode
            has the value of disable(2), the value of 
            stpxFastStartPortEnable for the same instance will be 
            false(2). When the stpxFastStartPortMode has the value 
            of default(4), the value of stpxFastStartPortEnable for 
            the same instance depends on the object value of 
            stpxFastStartGlobalDefaultMode.";
          smiv2:defval "false";
          smiv2:max-access "read-write";
          smiv2:oid "1.3.6.1.4.1.9.9.82.1.9.3.1.2";
        }

        leaf stpxFastStartPortMode {
          type enumeration {
            enum "enable" {
              value "1";
            }
            enum "disable" {
              value "2";
            }
            enum "enableForTrunk" {
              value "3";
            }
            enum "default" {
              value "4";
            }
            enum "network" {
              value "5";
            }
          }
          description
           "Indicates the mode of Fast Start Feature on the 
            port. A port with fast start enabled is immediately 
            put in spanning tree forwarding state when the port
            is detected by the Spanning Tree, rather than 
            starting in blocking state which is the normal 
            operation.
            
            enable -- the fast start feature is enabled on this 
                      port but will only take effect when the 
                      object value of its 
                      vlanTrunkPortDynamicStatus as specified 
                      in CISCO-VTP-MIB is notTrunking(2).
            
            disable -- the fast start feature is disabled on this 
                      port.  
            
            enableForTrunk -- the fast start feature is enabled 
                      on this port and will take effect 
                      regardless of the object value of 
                      its vlanTrunkPortDynamicStatus.
            
            default -- whether the fast start feature is enabled
                       or not on this port depends on the object 
                       value of stpxFastStartGlobalDefaultMode.
            
            network -- the fast start network mode is enabled on 
                       this port.";
          smiv2:max-access "read-write";
          smiv2:oid "1.3.6.1.4.1.9.9.82.1.9.3.1.3";
        }

        leaf stpxFastStartPortBpduGuardMode {
          type enumeration {
            enum "enable" {
              value "1";
            }
            enum "disable" {
              value "2";
            }
            enum "default" {
              value "3";
            }
          }
          description
           "Indicates the mode of Bpdu Guard Feature on the
            port. A port with Bpdu Guard enabled is 
            immediately disabled when the system 
            receives a BPDU from that port. 
            
            enable -- the Bpdu Guard feature is enabled on this
                      port. 
            
            disable -- the Bpdu Guard feature is disabled on this
                      port.
            
            default -- whether the Bpdu Guard feature is enabled
                       or not on this port depends on the object
                       value of stpxFastStartBpduGuardEnable. If 
                       the value of stpxFastStartBpduGuardEnable
                       is true(1) and Fast Start feature is also 
                       enabled operationally on this port, then
                       this port is immediately disabled when 
                       the system receives a BPDU from this port.";
          smiv2:defval "default";
          smiv2:max-access "read-write";
          smiv2:oid "1.3.6.1.4.1.9.9.82.1.9.3.1.4";
        }

        leaf stpxFastStartPortBpduFilterMode {
          type enumeration {
            enum "enable" {
              value "1";
            }
            enum "disable" {
              value "2";
            }
            enum "default" {
              value "3";
            }
          }
          description
           "Indicates the mode of Bpdu Filter Feature on the
            port. The system will not transmit BPDUs on a port 
            with Bpdu Filter feature enabled.
            
            enable -- the Bpdu Filter feature is enabled on this 
                      port. 
            
            disable -- the Bpdu Filter feature is disabled on this
                       port.
            
            default -- whether the Bpdu Filter feature is enabled
                       or not on this port depends on the object
                       value of stpxFastStartBpduFilterEnable. If
                       the value of stpxFastStartBpduFilterEnable
                       is true(1) and Fast Start feature is also
                       enabled operationally on this port, then
                       no BPDUs will be transmitted on this port.";
          smiv2:defval "default";
          smiv2:max-access "read-write";
          smiv2:oid "1.3.6.1.4.1.9.9.82.1.9.3.1.5";
        }
      }
    }

    container stpxFastStartOperModeTable {
      description
       "A table containing a list of the bridge ports 
        for a particular Spanning Tree Instance.";
      smiv2:oid "1.3.6.1.4.1.9.9.82.1.9.5";

      list stpxFastStartOperModeEntry {
        key "stpxFastStartOperModeInstIndex stpxFastStartOperModePortIndex";
        description
         "An entry with port fast start oper mode 
          information on a bridge port for a particular 
          Spanning Tree Instance.";
        smiv2:oid "1.3.6.1.4.1.9.9.82.1.9.5.1";

        leaf stpxFastStartOperModeInstIndex {
          type int32 {
            range "0..65535";
          }
          description
           "The Spanning Tree instance id, such as the VLAN id 
            of the VLAN if the object value of stpxSpanningTreeType
            is pvstPlus(1).";
          smiv2:max-access "not-accessible";
          smiv2:oid "1.3.6.1.4.1.9.9.82.1.9.5.1.1";
        }

        leaf stpxFastStartOperModePortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.9.5.1.2";
        }

        leaf stpxFastStartOperMode {
          type enumeration {
            enum "enabled" {
              value "1";
            }
            enum "disabled" {
              value "2";
            }
          }
          description
           "Indicates the fast start operational status of the 
            port on a particular Spanning Tree Instance.";
          smiv2:max-access "read-only";
          smiv2:oid "1.3.6.1.4.1.9.9.82.1.9.5.1.3";
        }
      }
    }

    container stpxBpduSkewingTable {
      description
       "A table containing a list of the bridge ports for 
        which a particular Spanning Tree instance has been 
        detected to have BPDU skewing occurred since the 
        object value of stpxBpduSkewingDetectionEnable was
        last changed to true(1).
        
        The agent creates a new entry in this table whenever
        a port in a particular Spanning Tree instance is 
        detected to be BPDU skewed since the object value of 
        stpxBpduSkewingDetectionEnable object is changed to 
        true(1). The agent deletes all the entries in this 
        table when the object value of 
        stpxBpduSkewingDetectionEnable is changed to false(2)
        or the object value of stpxSpanningTreeType is 
        changed.";
      smiv2:oid "1.3.6.1.4.1.9.9.82.1.10.2";

      list stpxBpduSkewingEntry {
        key "stpxBpduSkewingInstanceIndex stpxBpduSkewingPortIndex";
        description
         "A Spanning Tree instance on a particular port for
          which BPDU skewing has been detected.";
        smiv2:oid "1.3.6.1.4.1.9.9.82.1.10.2.1";

        leaf stpxBpduSkewingInstanceIndex {
          type int32 {
            range "0..65535";
          }
          description
           "The Spanning Tree instance id, such as the VLAN id 
            of the VLAN if the object value of stpxSpanningTreeType 
            is pvstPlus(1).";
          smiv2:max-access "not-accessible";
          smiv2:oid "1.3.6.1.4.1.9.9.82.1.10.2.1.1";
        }

        leaf stpxBpduSkewingPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.10.2.1.2";
        }

        leaf stpxBpduSkewingLastSkewDuration {
          type uint32;
          units "milliseconds";
          description
           "Indicates the skew duration in milliseconds of the
            last BPDU skewing detected.";
          smiv2:max-access "read-only";
          smiv2:oid "1.3.6.1.4.1.9.9.82.1.10.2.1.3";
        }

        leaf stpxBpduSkewingWorstSkewDuration {
          type uint32;
          units "milliseconds";
          description
           "Indicates the skew duration in milliseconds of the
            worst BPDU skewing detected.";
          smiv2:max-access "read-only";
          smiv2:oid "1.3.6.1.4.1.9.9.82.1.10.2.1.4";
        }

        leaf stpxBpduSkewingWorstSkewTime {
          type yang:timestamp;
          description
           "Indicates the value of sysUpTime when the worst
            BPDU skewing was detected.";
          smiv2:max-access "read-only";
          smiv2:oid "1.3.6.1.4.1.9.9.82.1.10.2.1.5";
        }
      }
    }

    container stpxMSTInstanceTable {
      status deprecated;
      description
       "This table contains MST instance information with
        one entry for an MST instance within the range of 
        0 to the object value of stpxMSTMaxInstanceNumber. 
        
        This table is deprecated and replaced by 
        stpxSMSTInstanceTable.";
      smiv2:oid "1.3.6.1.4.1.9.9.82.1.11.4";

      list stpxMSTInstanceEntry {
        key "stpxMSTInstanceIndex";
        status deprecated;
        description
         "A conceptual row containing the MST instance 
          information.";
        smiv2:oid "1.3.6.1.4.1.9.9.82.1.11.4.1";

        leaf stpxMSTInstanceIndex {
          type int32 {
            range "0..256";
          }
          status deprecated;
          description
           "An integer that uniquely identifies an MST instance 
            within the range of 0 to the object value of
            stpxMSTMaxInstanceNumber.
            
            This object is deprecated and replaced by 
            stpxSMSTInstanceIndex.";
          smiv2:max-access "not-accessible";
          smiv2:oid "1.3.6.1.4.1.9.9.82.1.11.4.1.1";
        }

        leaf stpxMSTInstanceVlansMapped {
          type binary {
            length "0..128";
          }
          status deprecated;
          description
           "A string of octets containing one bit per VLAN. The
            first octet corresponds to VLANs with VlanIndex values
            of 0 through 7; the second octet to VLANs 8 through
            15; etc.  The most significant bit of each octet
            corresponds to the lowest value VlanIndex in that octet.
            
            For each VLAN, if it is mapped to this MST instance, 
            then the bit corresponding to that VLAN is set to '1'.
            
            This object is deprecated and replaced by 
            stpxSMSTInstanceVlansMapped1k2k.";
          smiv2:max-access "read-only";
          smiv2:oid "1.3.6.1.4.1.9.9.82.1.11.4.1.2";
        }

        leaf stpxMSTInstanceVlansMapped2k {
          type binary {
            length "0..128";
          }
          status deprecated;
          description
           "A string of octets containing one bit per VLAN for
            VLANS with VlanIndex values of 1024 through 2047. The
            first octet corresponds to VLANs with VlanIndex values
            of 1024 through 1031; the second octet to VLANs 1032
            through 1039; etc.  The most significant bit of each
            octet corresponds to the lowest value VlanIndex in that
            octet.
            
            For each VLAN, if it is mapped to this MST instance, 
            then the bit corresponding to that VLAN is set to '1'.
            
            This object is deprecated and replaced by 
            stpxSMSTInstanceVlansMapped1k2k.";
          smiv2:max-access "read-only";
          smiv2:oid "1.3.6.1.4.1.9.9.82.1.11.4.1.3";
        }

        leaf stpxMSTInstanceVlansMapped3k {
          type binary {
            length "0..128";
          }
          status deprecated;
          description
           "A string of octets containing one bit per VLAN for
            VLANS with VlanIndex values of 2048 through 3071. The
            first octet corresponds to VLANs with VlanIndex values
            of 2048 through 2055; the second octet to VLANs 2056
            through 2063; etc.  The most significant bit of each
            octet corresponds to the lowest value VlanIndex in that
            octet.
            
            For each VLAN, if it is mapped to this MST instance, 
            then the bit corresponding to that VLAN is set to '1'.
            
            This object is deprecated and replaced by 
            stpxSMSTInstanceVlansMapped3k4k.";
          smiv2:max-access "read-only";
          smiv2:oid "1.3.6.1.4.1.9.9.82.1.11.4.1.4";
        }

        leaf stpxMSTInstanceVlansMapped4k {
          type binary {
            length "0..128";
          }
          status deprecated;
          description
           "A string of octets containing one bit per VLAN for
            VLANS with VlanIndex values of 3072 through 4095. The
            first octet corresponds to VLANs with VlanIndex values
            of 3072 through 3079; the second octet to VLANs 3080
            through 3087; etc.  The most significant bit of each
            octet corresponds to the lowest value VlanIndex in that
            octet.
            
            For each VLAN, if it is mapped to this MST instance, 
            then the bit corresponding to that VLAN is set to '1'.
            
            This object is deprecated and replaced by
            stpxSMSTInstanceVlansMapped3k4k.";
          smiv2:max-access "read-only";
          smiv2:oid "1.3.6.1.4.1.9.9.82.1.11.4.1.5";
        }

        leaf stpxMSTInstanceRemainingHopCount {
          type int32 {
            range "0..40";
          }
          status deprecated;
          description
           "The remaining hop count for this MST instance.
            
            This object will take on value of 40 if the object value
            of stpxSMSTInstanceRemainingHopCount is greater than 40.
            
            This object is only instantiated when the object value of
            stpxSpanningTreeType is mst(4).
            
            This object is deprecated and replaced by 
            stpxSMSTInstanceRemainingHopCount.";
          smiv2:max-access "read-only";
          smiv2:oid "1.3.6.1.4.1.9.9.82.1.11.4.1.6";
        }
      }
    }

    container stpxMSTInstanceEditTable {
      status deprecated;
      description
       "This table contains MST instance information in the 
        Edit Buffer with one entry for each MST
        instance numbered from 0 to stpxMSTMaxInstanceNumber. 
        
        This table is only instantiated when the 
        stpxMSTRegionEditBufferStatus has the value of
        acquiredBySnmp(2).
        
        This table is deprecated and replaced by 
        stpxSMSTInstanceEditTable.";
      smiv2:oid "1.3.6.1.4.1.9.9.82.1.11.9";

      list stpxMSTInstanceEditEntry {
        key "stpxMSTInstanceEditIndex";
        status deprecated;
        description
         "A conceptual row containing MST instance information 
          in the Edit Buffer.";
        smiv2:oid "1.3.6.1.4.1.9.9.82.1.11.9.1";

        leaf stpxMSTInstanceEditIndex {
          type int32 {
            range "0..256";
          }
          status deprecated;
          description
           "An integer that uniquely identifies an MST instance 
            from 0 to the object value of stpxMSTMaxInstanceNumber.
            
            The instances of this table entry with 
            stpxMSTInstanceEditIndex of zero can not be 
            modified.
            
            This object is deprecated and replaced by 
            stpxSMSTInstanceEditIndex.";
          smiv2:max-access "not-accessible";
          smiv2:oid "1.3.6.1.4.1.9.9.82.1.11.9.1.1";
        }

        leaf stpxMSTInstanceEditVlansMap {
          type binary {
            length "0..128";
          }
          status deprecated;
          description
           "A string of octets containing one bit per VLAN. The
            first octet corresponds to VLANs with VlanIndex values
            of 0 through 7; the second octet to VLANs 8 through
            15; etc.  The most significant bit of each octet
            corresponds to the lowest value VlanIndex in that octet.
            
            For each VLAN, if it is mapped to this MST instance, 
            then the bit corresponding to that VLAN is set to 
            '1'. Each VLAN can only be mapped to one unique MST 
            instance in the range from 1 to stpxMSTMaxInstanceNumber.
            If the bit corresponding to a VLAN is changed from '1' 
            to '0', then that VLAN will be automatically mapped to 
            MST instance 0 by the device.
            
            This object is deprecated and replaced by 
            stpxSMSTInstanceEditVlansMap1k2k.";
          smiv2:max-access "read-write";
          smiv2:oid "1.3.6.1.4.1.9.9.82.1.11.9.1.2";
        }

        leaf stpxMSTInstanceEditVlansMap2k {
          type binary {
            length "0..128";
          }
          status deprecated;
          description
           "A string of octets containing one bit per VLAN for
            VLANS with VlanIndex values of 1024 through 2047. The
            first octet corresponds to VLANs with VlanIndex values
            of 1024 through 1031; the second octet to VLANs 1032
            through 1039; etc.  The most significant bit of each
            octet corresponds to the lowest value VlanIndex in that
            octet.
            
            For each VLAN, if it is mapped to this MST instance,
            then the bit corresponding to that VLAN is set to
            '1'. Each VLAN can only be mapped to one unique MST
            instance in the range from 1 to stpxMSTMaxInstanceNumber.
            If the bit corresponding to a VLAN is changed from '1' 
            to '0', then that VLAN will be automatically mapped to 
            MST instance 0 by the device.
            
            This object is deprecated and replaced by 
            stpxSMSTInstanceEditVlansMap1k2k.";
          smiv2:max-access "read-write";
          smiv2:oid "1.3.6.1.4.1.9.9.82.1.11.9.1.3";
        }

        leaf stpxMSTInstanceEditVlansMap3k {
          type binary {
            length "0..128";
          }
          status deprecated;
          description
           "A string of octets containing one bit per VLAN for
            VLANS with VlanIndex values of 2048 through 3071. The
            first octet corresponds to VLANs with VlanIndex values
            of 2048 through 2055; the second octet to VLANs 2056
            through 2063; etc.  The most significant bit of each
            octet corresponds to the lowest value VlanIndex in that
            octet.
            
            For each VLAN, if it is mapped to this MST instance,
            then the bit corresponding to that VLAN is set to
            '1'. Each VLAN can only be mapped to one unique MST
            instance in the range from 1 to stpxMSTMaxInstanceNumber.
            If the bit corresponding to a VLAN is changed from '1' 
            to '0', then that VLAN will be automatically mapped to 
            MST instance 0 by the device.
            
            This object is deprecated and replaced by 
            stpxSMSTInstanceEditVlansMap3k4k.";
          smiv2:max-access "read-write";
          smiv2:oid "1.3.6.1.4.1.9.9.82.1.11.9.1.4";
        }

        leaf stpxMSTInstanceEditVlansMap4k {
          type binary {
            length "0..128";
          }
          status deprecated;
          description
           "A string of octets containing one bit per VLAN for
            VLANS with VlanIndex values of 3072 through 4095. The
            first octet corresponds to VLANs with VlanIndex values
            of 3072 through 3079; the second octet to VLANs 3080
            through 3087; etc.  The most significant bit of each
            octet corresponds to the lowest value VlanIndex in that
            octet.
            
            For each VLAN, if it is mapped to this MST instance,
            then the bit corresponding to that VLAN is set to
            '1'. Each VLAN can only be mapped to one unique MST
            instance in the range from 1 to stpxMSTMaxInstanceNumber.
            If the bit corresponding to a VLAN is changed from '1' 
            to '0', then that VLAN will be automatically mapped to 
            MST instance 0 by the device.
            
            This object is deprecated and replaced by
            stpxSMSTInstanceEditVlansMap3k4k.";
          smiv2:max-access "read-write";
          smiv2:oid "1.3.6.1.4.1.9.9.82.1.11.9.1.5";
        }
      }
    }

    container stpxMSTPortTable {
      status deprecated;
      description
       "A table containing port information for the MST 
        Protocol on all the bridge ports existing on the 
        system.";
      smiv2:oid "1.3.6.1.4.1.9.9.82.1.11.11";

      list stpxMSTPortEntry {
        key "stpxMSTPortIndex";
        status deprecated;
        description
         "An entry with port information for the MST Protocol
          on a bridge port.";
        smiv2:oid "1.3.6.1.4.1.9.9.82.1.11.11.1";

        leaf stpxMSTPortIndex {
          type int32 {
            range "1..65535";
          }
          status deprecated;
          description
           "The value of dot1dBasePort (i.e. dot1dBridge.1.4)
            for the bridge port.";
          reference
           "dot1dBasePort is defined in RFC1493.";
          smiv2:max-access "not-accessible";
          smiv2:oid "1.3.6.1.4.1.9.9.82.1.11.11.1.1";
        }

        leaf stpxMSTPortAdminLinkType {
          type enumeration {
            enum "pointToPoint" {
              value "1";
            }
            enum "shared" {
              value "2";
            }
            enum "auto" {
              value "3";
            }
          }
          status deprecated;
          description
           "Indicates the administrative link type configuration of 
            a bridge port for the MST protocol. 
            
            pointToPoint -- the port is administratively configured to
                    be connected to a point-to-point link.
            
            shared -- the port is administratively configured to be
                    connected to a shared medium. 
            
            auto -- the administrative configuration of the port's 
                    link type depends on link duplex of the port.
                    If the port link is full-duplex, the administrative 
                    link type configuration on this port will be taken 
                    as pointTopoint(1). If the port link is half-duplex, 
                    the administrative link type configuration on this
                    port will be taken as shared(2).
            
            This configuration of this object only takes effect when the
            stpxSpanningTreeType is mst(4) or rapidPvstPlus(5).
            stpxMSTPortAdminLinkType is deprecated and replaced 
            with stpxRSTPPortAdminLinkType.";
          smiv2:defval "auto";
          smiv2:max-access "read-write";
          smiv2:oid "1.3.6.1.4.1.9.9.82.1.11.11.1.2";
        }

        leaf stpxMSTPortOperLinkType {
          type enumeration {
            enum "pointToPoint" {
              value "1";
            }
            enum "shared" {
              value "2";
            }
            enum "other" {
              value "3";
            }
          }
          status deprecated;
          description
           "Indicates the operational link type of a bridge port
            for the MST protocol.
            
            pointToPoint -- the port is operationally connected to
                    a point-to-point link.
            
            shared -- the port is operationally connected to 
                    a shared medium.
            
            other -- none of the above.
            
            This object is only instantiated when the object value of
            stpxSpanningTreeType is mst(4).  stpxMSTPortOperLinkType 
            is deprecated and replaced with stpxRSTPPortOperLinkType.";
          smiv2:max-access "read-only";
          smiv2:oid "1.3.6.1.4.1.9.9.82.1.11.11.1.3";
        }

        leaf stpxMSTPortProtocolMigration {
          type boolean;
          status deprecated;
          description
           "The protocol migration control on this port. When the 
            object value of  stpxSpanningTreeType is mst(4) or 
            rapidPvstPlus(5), setting true(1) to this object forces 
            the device to try using version 2 BPDUs on this port. 
            When the object value of stpxSpanningTreeType is neither 
            mst(4) nor rapidPvstPlus(5), setting true(1) to this 
            object has no effect. Setting false(2) to this object has 
            no effect. This object always returns false(2) when read.
            stpxMSTPortProtocolMigration is deprecated and 
            replaced with stpxRSTPPortProtocolMigration.";
          reference
           "IEEE 802.1w clause 14.8.2.4, 17.26.";
          smiv2:max-access "read-write";
          smiv2:oid "1.3.6.1.4.1.9.9.82.1.11.11.1.4";
        }

        leaf stpxMSTPortStatus {
          type bits {
            bit edge {
              position "0";
            }
            bit boundary {
              position "1";
            }
            bit pvst {
              position "2";
            }
            bit stp {
              position "3";
            }
          }
          status deprecated;
          description
           "Indicates the operational status of the port for the 
            MST protocol. 
            
            edge -- this port is an edge port for the MST region.
            
            boundary -- this port is a boundary port for the 
                    MST region.
            
            pvst --  this port is connected to a PVST/PVST+ bridge.   
            
            stp -- this port is connected to a Single Spanning
                    Tree bridge. 
            
            This object is only instantiated when the object value
            of stpxSpanningTreeType is mst(4).
            
            This object is deprecated and replaced by 
            stpxSMSTPortStatus.";
          smiv2:max-access "read-only";
          smiv2:oid "1.3.6.1.4.1.9.9.82.1.11.11.1.5";
        }
      }
    }

    container stpxMSTPortRoleTable {
      status deprecated;
      description
       "A table containing a list of the bridge ports for a 
        particular MST instance.  This table is only instantiated 
        when the stpxSpanningTreeType is mst(4). 
        
        This table is deprecated and replaced with 
        stpxRSTPPortRoleTable.";
      smiv2:oid "1.3.6.1.4.1.9.9.82.1.11.12";

      list stpxMSTPortRoleEntry {
        key "stpxMSTPortRoleInstanceIndex stpxMSTPortRolePortIndex";
        status deprecated;
        description
         "An entry containing the port role information for the MST
          protocol on a port for a particular MST instance existing
          on the system.";
        smiv2:oid "1.3.6.1.4.1.9.9.82.1.11.12.1";

        leaf stpxMSTPortRoleInstanceIndex {
          type int32 {
            range "0..256";
          }
          status deprecated;
          description
           "The MST instance id within the range of 0 to
            stpxMSTMaxInstanceNumber.";
          smiv2:max-access "not-accessible";
          smiv2:oid "1.3.6.1.4.1.9.9.82.1.11.12.1.1";
        }

        leaf stpxMSTPortRolePortIndex {
          type int32 {
            range "1..65535";
          }
          status deprecated;
          description
           "The value of dot1dBasePort (i.e. dot1dBridge.1.4)
            for the bridge port.";
          reference
           "dot1dBasePort is defined in RFC1493.";
          smiv2:max-access "not-accessible";
          smiv2:oid "1.3.6.1.4.1.9.9.82.1.11.12.1.2";
        }

        leaf stpxMSTPortRoleValue {
          type enumeration {
            enum "disabled" {
              value "1";
            }
            enum "root" {
              value "2";
            }
            enum "designated" {
              value "3";
            }
            enum "alternate" {
              value "4";
            }
            enum "backUp" {
              value "5";
            }
            enum "boundary" {
              value "6";
            }
            enum "master" {
              value "7";
            }
          }
          status deprecated;
          description
           "Indicates the port role on a particular MST instance
            for the MST protocol. 
            
            disabled --  this port has no role on this MST instance. 
            
            root -- this port has the role of root port on this MST
                        instance. 
            
            designated -- this port has the role of designated 
                        port on this MST instance.
            
            alternate -- this port has the role of alternate port
                        on this MST instance.
            
            backUp -- this port has the role of backup port on this  
                        MST instance.
            
            boundary -- this port has the role of boundary port on 
                        this MST instance.
            
            master -- this port has the role of master port on
                      this MST instance.";
          smiv2:max-access "read-only";
          smiv2:oid "1.3.6.1.4.1.9.9.82.1.11.12.1.3";
        }
      }
    }

    container stpxRSTPPortTable {
      description
       "A table containing port information for the RSTP 
        Protocol on all the bridge ports existing in the 
        system.";
      smiv2:oid "1.3.6.1.4.1.9.9.82.1.12.1";

      list stpxRSTPPortEntry {
        key "stpxRSTPPortIndex";
        description
         "An entry with port information for the RSTP Protocol
          on a bridge port.";
        smiv2:oid "1.3.6.1.4.1.9.9.82.1.12.1.1";

        leaf stpxRSTPPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.12.1.1.1";
        }

        leaf stpxRSTPPortAdminLinkType {
          type enumeration {
            enum "pointToPoint" {
              value "1";
            }
            enum "shared" {
              value "2";
            }
            enum "auto" {
              value "3";
            }
          }
          description
           "Indicates the administrative link type configuration of 
            a bridge port for the RSTP protocol. 
            
            pointToPoint -- the port is administratively configured to
                    be connected to a point-to-point link.
            
            shared -- the port is administratively configured to be
                    connected to a shared medium. 
            
            auto -- the administrative configuration of the port's 
                    link type depends on link duplex of the port.
                    If the port link is full-duplex, the administrative 
                    link type configuration on this port will be taken 
                    as pointTopoint(1). If the port link is half-duplex, 
                    the administrative link type configuration on this
                    port will be taken as shared(2).
            
            This configuration of this object only takes effect when the
            stpxSpanningTreeType is mst(4) or rapidPvstPlus(5).";
          smiv2:defval "auto";
          smiv2:max-access "read-write";
          smiv2:oid "1.3.6.1.4.1.9.9.82.1.12.1.1.2";
        }

        leaf stpxRSTPPortOperLinkType {
          type enumeration {
            enum "pointToPoint" {
              value "1";
            }
            enum "shared" {
              value "2";
            }
            enum "other" {
              value "3";
            }
          }
          description
           "Indicates the operational link type of a bridge port
            for the RSTP protocol.
            
            pointToPoint -- the port is operationally connected to
                    a point-to-point link.
            
            shared -- the port is operationally connected to 
                    a shared medium.
            
            other -- none of the above.
            
            This object is only instantiated when the object value of
            stpxSpanningTreeType is mst(4) or rapidPvstPlus(5).";
          smiv2:max-access "read-only";
          smiv2:oid "1.3.6.1.4.1.9.9.82.1.12.1.1.3";
        }

        leaf stpxRSTPPortProtocolMigration {
          type boolean;
          description
           "The protocol migration control on this port. When the 
            object value of  stpxSpanningTreeType is mst(4) or 
            rapidPvstPlus(5), setting true(1) to this object forces 
            the device to try using version 2 BPDUs on this port. 
            When the object value of stpxSpanningTreeType is neither 
            mst(4) nor rapidPvstPlus(5), setting true(1) to 
            this object has no effect. Setting false(2) to this 
            object has no effect. This object always returns 
            false(2) when read.";
          reference
           "IEEE 802.1w clause 14.8.2.4, 17.26.";
          smiv2:max-access "read-write";
          smiv2:oid "1.3.6.1.4.1.9.9.82.1.12.1.1.4";
        }
      }
    }

    container stpxRSTPPortRoleTable {
      description
       "A table containing a list of the bridge ports for a 
        particular Spanning Tree instance.  This table is 
        only instantiated when the stpxSpanningTreeType is mst(4) 
        or rapidPvstPlus(5).";
      smiv2:oid "1.3.6.1.4.1.9.9.82.1.12.2";

      list stpxRSTPPortRoleEntry {
        key "stpxRSTPPortRoleInstanceIndex stpxRSTPPortRolePortIndex";
        description
         "An entry containing the port role information for the RSTP
          protocol on a port for a particular Spanning Tree instance.";
        smiv2:oid "1.3.6.1.4.1.9.9.82.1.12.2.1";

        leaf stpxRSTPPortRoleInstanceIndex {
          type int32 {
            range "0..4095";
          }
          description
           "The Spanning Tree instance id, it can either be a 
            VLAN number if the stpxSpanningTreeType is rapidPvstPlus(5) 
            or an MST instance id if the stpxSpanningTreeType is mst(4).";
          smiv2:max-access "not-accessible";
          smiv2:oid "1.3.6.1.4.1.9.9.82.1.12.2.1.1";
        }

        leaf stpxRSTPPortRolePortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.12.2.1.2";
        }

        leaf stpxRSTPPortRoleValue {
          type enumeration {
            enum "disabled" {
              value "1";
            }
            enum "root" {
              value "2";
            }
            enum "designated" {
              value "3";
            }
            enum "alternate" {
              value "4";
            }
            enum "backUp" {
              value "5";
            }
            enum "boundary" {
              value "6";
            }
            enum "master" {
              value "7";
            }
          }
          description
           "Indicates the port role on a particular Spanning Tree 
            instance for the RSTP protocol. 
            
            disabled --  this port has no role in this Spanning
                        Tree instance. 
            
            root -- this port has the role of root port in this
                        Spanning Tree instance. 
            
            designated -- this port has the role of designated 
                        port in this Spanning Tree instance.
            
            alternate -- this port has the role of alternate port
                        in this Spanning Tree instance.
            
            backUp -- this port has the role of backup port in this  
                        Spanning Tree instance.
            
            boundary -- this port has the role of boundary port in 
                        this Spanning Tree instance.
            
            master -- this port has the role of master port in
                        this Spanning Tree instance.
            
            This object could have a value of 'boundary' or 'master'
            only when the object value of stpxSpanningTreeType is mst(4).";
          smiv2:max-access "read-only";
          smiv2:oid "1.3.6.1.4.1.9.9.82.1.12.2.1.3";
        }
      }
    }

    container stpxRPVSTPortTable {
      description
       "A table containing a list of the bridge ports 
        for a particular Spanning Tree Instance.
        This table is only instantiated when the object value
        of stpxSpanningTreeType is rapidPvstPlus(5).";
      smiv2:oid "1.3.6.1.4.1.9.9.82.1.13.1";

      list stpxRPVSTPortEntry {
        key "stpxRPVSTPortVlanIndex stpxRPVSTPortIndex";
        description
         "An entry with port status information on a 
          bridge port for a particular Spanning Tree 
          Instance.";
        smiv2:oid "1.3.6.1.4.1.9.9.82.1.13.1.1";

        leaf stpxRPVSTPortVlanIndex {
          type cisco-vtp:VlanIndex;
          description
           "The VLAN id of the VLAN.";
          smiv2:max-access "not-accessible";
          smiv2:oid "1.3.6.1.4.1.9.9.82.1.13.1.1.1";
        }

        leaf stpxRPVSTPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.13.1.1.2";
        }

        leaf stpxRPVSTPortStatus {
          type bits {
            bit edge {
              position "0";
            }
            bit unused1 {
              position "1";
            }
            bit unused2 {
              position "2";
            }
            bit stp {
              position "3";
            }
            bit dispute {
              position "4";
            }
          }
          description
           "Indicates the operational status of the port for the 
            Rapid PVST+ protocol.
            
            edge -- this port is an edge port for the RST region.
            
            unused1 -- unused bit 1.
            
            unused2 -- unused bit 2.
            
            stp -- this port is connected to a Single Spanning
                   Tree/PVST+ bridge.
            
            dispute -- this port, as a designated port, received an
                   inferior BPDU with a designated role and the
                   learning bit being set.";
          smiv2:max-access "read-only";
          smiv2:oid "1.3.6.1.4.1.9.9.82.1.13.1.1.3";
        }
      }
    }

    container stpxSMSTInstanceTable {
      description
       "This table contains MST instance information
        for IEEE MST.";
      smiv2:oid "1.3.6.1.4.1.9.9.82.1.14.5";

      list stpxSMSTInstanceEntry {
        key "stpxSMSTInstanceIndex";
        description
         "A conceptual row containing the MST instance 
          information for IEEE MST.";
        smiv2:oid "1.3.6.1.4.1.9.9.82.1.14.5.1";

        leaf stpxSMSTInstanceIndex {
          type uint32;
          description
           "The MST instance ID, the value of which is in the range 
            from 0 to stpxSMSTMaxInstanceID.";
          smiv2:max-access "not-accessible";
          smiv2:oid "1.3.6.1.4.1.9.9.82.1.14.5.1.1";
        }

        leaf stpxSMSTInstanceVlansMapped1k2k {
          type binary {
            length "0..256";
          }
          description
           "A string of octets containing one bit per VLAN for
            VLANS with VlanIndex values of 0 through 2047. The
            first octet corresponds to VLANs with VlanIndex values
            of 0 through 7; the second octet to VLANs 8 through
            15; etc.  The most significant bit of each octet
            corresponds to the lowest value VlanIndex in that octet.
            
            For each VLAN, if it is mapped to this MST instance,
            then the bit corresponding to that VLAN is set to '1'.
            If the length of this string is less than 256 octets,
            any 'missing' octets are assumed to contain the value 
            of zero.";
          smiv2:max-access "read-only";
          smiv2:oid "1.3.6.1.4.1.9.9.82.1.14.5.1.2";
        }

        leaf stpxSMSTInstanceVlansMapped3k4k {
          type binary {
            length "0..256";
          }
          description
           "A string of octets containing one bit per VLAN for
            VLANS with VlanIndex values of 2048 through 4095. The
            first octet corresponds to VLANs with VlanIndex values
            of 2048 through 2055; the second octet to VLANs 2056
            through 2063; etc.  The most significant bit of each
            octet corresponds to the lowest value VlanIndex in that
            octet.
            
            For each VLAN, if it is mapped to this MST instance,
            then the bit corresponding to that VLAN is set to '1'.
            If the length of this string is less than 256 octets,
            any 'missing' octets are assumed to contain the value 
            of zero.";
          smiv2:max-access "read-only";
          smiv2:oid "1.3.6.1.4.1.9.9.82.1.14.5.1.3";
        }

        leaf stpxSMSTInstanceRemainingHopCount {
          type int32 {
            range "-1..2147483647";
          }
          description
           "The remaining hop count for this MST instance. If this object
            value is not applicable on an MST instance, then the value
            retrieved for this object for that MST instance will be -1. 
            
            This object is only instantiated when the object value of
            stpxSpanningTreeType is mst(4).";
          smiv2:max-access "read-only";
          smiv2:oid "1.3.6.1.4.1.9.9.82.1.14.5.1.4";
        }

        leaf stpxSMSTInstanceCISTRegionalRoot {
          type binary {
            length "8";
          }
          description
           "Indicates the Bridge Identifier (refer to BridgeId 
            defined in BRIDGE-MIB) of CIST (Common and Internal 
            Spanning Tree) Regional Root for the MST region.
            
            This object is only instantiated when the object value of
            stpxSpanningTreeType is mst(4) and stpxSMSTInstanceIndex
            is 0.";
          reference
           "IEEE 802.1S-2002: Section 13.9.";
          smiv2:max-access "read-only";
          smiv2:oid "1.3.6.1.4.1.9.9.82.1.14.5.1.5";
        }

        leaf stpxSMSTInstanceCISTIntRootCost {
          type uint32;
          description
           "Indicates the CIST Internal Root Path Cost, i.e., the
            path cost to the CIST Regional Root as specified by the
            corresponding stpxSMSTInstanceCISTRegionalRoot for the 
            MST region.
            
            This object is only instantiated when the object value of
            stpxSpanningTreeType is mst(4) and stpxSMSTInstanceIndex
            is 0.";
          reference
           "IEEE 802.1S-2002: Section 13.9.";
          smiv2:max-access "read-only";
          smiv2:oid "1.3.6.1.4.1.9.9.82.1.14.5.1.6";
        }
      }
    }

    container stpxSMSTInstanceEditTable {
      description
       "This table contains MST instance information in the 
        Edit Buffer. 
        
        This table is only instantiated when the object value
        of  stpxMSTRegionEditBufferStatus has the value of
        acquiredBySnmp(2).";
      smiv2:oid "1.3.6.1.4.1.9.9.82.1.14.6";

      list stpxSMSTInstanceEditEntry {
        key "stpxSMSTInstanceEditIndex";
        description
         "A conceptual row containing MST instance information 
          in the Edit Buffer.
          
          The total number of entries in this table has to be 
          less than or equal to the object value of stpxSMSTMaxInstances.";
        smiv2:oid "1.3.6.1.4.1.9.9.82.1.14.6.1";

        leaf stpxSMSTInstanceEditIndex {
          type uint32;
          description
           "The MST instance ID, the value of which is in the range from
            0 to stpxSMSTMaxInstanceID. 
            
            The instances of this table entry with 
            stpxSMSTInstanceEditIndex of zero is automatically
            created by the device and can not modified.";
          smiv2:max-access "not-accessible";
          smiv2:oid "1.3.6.1.4.1.9.9.82.1.14.6.1.1";
        }

        leaf stpxSMSTInstanceEditVlansMap1k2k {
          type binary {
            length "0..256";
          }
          description
           "A string of octets containing one bit per VLAN for
            VLANS with VlanIndex values of 0 through 2047. The
            first octet corresponds to VLANs with VlanIndex values
            of 0 through 7; the second octet to VLANs 8 through
            15; etc.  The most significant bit of each octet
            corresponds to the lowest value VlanIndex in that octet.
            
            For each VLAN, if it is mapped to this MST instance, 
            then the bit corresponding to that VLAN is set to 
            '1'. Each VLAN can only be mapped to one unique MST 
            instance with the range from 0 to stpxSMSTMaxInstanceNumber.
            If the bit corresponding to a VLAN is changed from '1' 
            to '0', then that VLAN will be automatically mapped to 
            SMST instance 0 by the device. If the bit corresponding 
            to a VLAN is changed from '0' to '1', then that VLAN will 
            be automatically removed from the MST instance this VLAN was 
            previously mapped to. If the length of this string is 
            less than 256 octets, any 'missing' octets are assumed to 
            contain the value of zero.";
          smiv2:max-access "read-write";
          smiv2:oid "1.3.6.1.4.1.9.9.82.1.14.6.1.2";
        }

        leaf stpxSMSTInstanceEditVlansMap3k4k {
          type binary {
            length "0..256";
          }
          description
           "A string of octets containing one bit per VLAN for
            VLANS with VlanIndex values of 2048 through 4095. The
            first octet corresponds to VLANs with VlanIndex values
            of 2048 through 2055; the second octet to VLANs 2056 through
            2063; etc.  The most significant bit of each octet
            corresponds to the lowest value VlanIndex in that octet.
            
            For each VLAN, if it is mapped to this MST instance,
            then the bit corresponding to that VLAN is set to
            '1'. Each VLAN can only be mapped to one unique MST
            instance with the range from 0 to stpxSMSTMaxInstanceNumber.
            If the bit corresponding to a VLAN is changed from '1'
            to '0', then that VLAN will be automatically mapped to
            SMST instance 0 by the device. If the bit corresponding
            to a VLAN is changed from '0' to '1', then that VLAN will
            be automatically removed from the MST instance this VLAN was
            previously mapped to. If the length of this string is 
            less than 256 octets, any 'missing' octets are assumed to 
            contain the value of zero.";
          smiv2:max-access "read-write";
          smiv2:oid "1.3.6.1.4.1.9.9.82.1.14.6.1.3";
        }

        leaf stpxSMSTInstanceEditRowStatus {
          type snmpv2-tc:RowStatus;
          description
           "This object controls the creation and deletion of a row 
            in stpxSMSTInstanceEditTable.
            
            When creating an entry in this table, 'createAndGo' method
            is used and the value of this object is set to 'active'.
            Deactivation of an 'active' entry is not allowed.  When 
            deleting an entry in this table, 'destroy' method is used. 
            Once a row becomes active, value in any other column 
            within such a row may be modified. When a row is active, 
            setting the instance of stpxSMSTInstanceEditVlansMap1k2k
            stpxSMSTInstanceEditVlansMap3k4k for the same MST instance
            both to the value of zero length can not be allowed.";
          smiv2:max-access "read-write";
          smiv2:oid "1.3.6.1.4.1.9.9.82.1.14.6.1.4";
        }
      }
    }

    container stpxSMSTPortTable {
      description
       "A table containing port information for the MST 
        Protocol on all the bridge ports existing on the 
        system.
        
        This table is only instantiated when the object 
        value of stpxSpanningTreeType is mst(4)";
      smiv2:oid "1.3.6.1.4.1.9.9.82.1.14.7";

      list stpxSMSTPortEntry {
        key "stpxSMSTPortIndex";
        description
         "An entry with port information for the MST protocol
          on a bridge port.";
        smiv2:oid "1.3.6.1.4.1.9.9.82.1.14.7.1";

        leaf stpxSMSTPortIndex {
          type int32 {
            range "1..65535";
          }
          description
           "The value of dot1dBasePort (i.e. dot1dBridge.1.4)
            for the bridge port.";
          reference
           "dot1dBasePort is defined in RFC1493.";
          smiv2:max-access "not-accessible";
          smiv2:oid "1.3.6.1.4.1.9.9.82.1.14.7.1.1";
        }

        leaf stpxSMSTPortStatus {
          type bits {
            bit edge {
              position "0";
            }
            bit boundary {
              position "1";
            }
            bit pvst {
              position "2";
            }
            bit stp {
              position "3";
            }
            bit dispute {
              position "4";
            }
            bit rstp {
              position "5";
            }
          }
          description
           "Indicates the operational status of the port for the 
            MST protocol. 
            
            edge -- this port is an edge port for the MST region.
            
            boundary -- this port is a boundary port for the 
                    MST region.
            
            pvst --  this port is connected to a PVST/PVST+ bridge.   
            
            stp -- this port is connected to a Single Spanning
                    Tree bridge.
            
            dispute -- this port, as a designated port, received an
                    inferior BPDU with a designated role and the
                    learning bit being set.
            
            rstp -- this port is connected to a RSTP bridge or an 
                    MST bridge in a different MST region.";
          smiv2:max-access "read-only";
          smiv2:oid "1.3.6.1.4.1.9.9.82.1.14.7.1.2";
        }

        leaf stpxSMSTPortAdminHelloTime {
          type uint32;
          units "hundredth of seconds";
          description
           "The adminitratively configured hello time in hundredth 
            of seconds on a port for IEEE MST. The granularity 
            of this timer is 1 second. An agent may return a badValue 
            error if a set is attempted to a value which is not a 
            whole number of seconds. This object value of zero
            means the hello time is not specifically configured on 
            this port and object value of stpxSMSTPortConfigedHelloTime
            retrieved for this port will take on the value of 
            dot1dStpBridgeHelloTime defined in BRIDGE-MIB.";
          smiv2:max-access "read-write";
          smiv2:oid "1.3.6.1.4.1.9.9.82.1.14.7.1.3";
        }

        leaf stpxSMSTPortConfigedHelloTime {
          type uint32;
          units "hundredth of seconds";
          description
           "Indicates the effective configuration of the hello time on 
            a port.";
          smiv2:max-access "read-only";
          smiv2:oid "1.3.6.1.4.1.9.9.82.1.14.7.1.4";
        }

        leaf stpxSMSTPortOperHelloTime {
          type int32 {
            range "-1..2147483647";
          }
          units "hundredth of seconds";
          description
           "The operational hello time in hundredth of seconds on a 
            port for IEEE MST. If this object value is not
            applicable on a port, then the value retrieved on that
            port will be -1.";
          smiv2:max-access "read-only";
          smiv2:oid "1.3.6.1.4.1.9.9.82.1.14.7.1.5";
        }

        leaf stpxSMSTPortAdminMSTMode {
          type enumeration {
            enum "preStandard" {
              value "1";
            }
            enum "auto" {
              value "2";
            }
          }
          description
           "The desired MST mode of this port.
            
            preStandard -- this port is administratively configured to
                transmit pre-standard, i.e. pre IEEE MST, BPDUs.
            
            auto -- the BPDU transmission mode of this port is based 
                on automatic detection of neighbor ports.";
          smiv2:max-access "read-write";
          smiv2:oid "1.3.6.1.4.1.9.9.82.1.14.7.1.6";
        }

        leaf stpxSMSTPortOperMSTMode {
          type enumeration {
            enum "unknown" {
              value "1";
            }
            enum "preStandard" {
              value "2";
            }
            enum "standard" {
              value "3";
            }
          }
          description
           "Indicates the current operational MST mode of this port.
            
            unknown -- the operational mode is currently unknown.
            
            preStandard -- this port is currently operating in 
                pre-standard MSTP BPDU transmission mode.
            
            standard -- this port is currently operating in IEEE MST 
                BPDU transmission mode.";
          smiv2:max-access "read-only";
          smiv2:oid "1.3.6.1.4.1.9.9.82.1.14.7.1.7";
        }
      }
    }
  }

  smiv2:alias "stpxPreferredVlansTable" {
    description
     "The table containing indications of which VLANs are
      preferred on which VLAN trunk ports.  The preferred
      VLANs on a trunk port have a lower Path Cost value
      compared with the VLANs on the trunk not in the
      preferred list. If the value of stpxSpanningTreeType 
      is neither pvstPlus(1) nor rapidPvstPlus(5), the 
      configuration in this table has no effect. ";
    smiv2:oid "1.3.6.1.4.1.9.9.82.1.2.1";
  }

  smiv2:alias "stpxPreferredVlansEntry" {
    description
     "An entry indicating which VLANs are preferred on a
      specific VLAN trunk port.";
    smiv2:oid "1.3.6.1.4.1.9.9.82.1.2.1.1";
  }

  augment "/cisco-vtp:CISCO-VTP-MIB/cisco-vtp:vlanTrunkPortTable/cisco-vtp:vlanTrunkPortEntry" {
    description
     "An entry indicating which VLANs are preferred on a
      specific VLAN trunk port.";
    smiv2:oid "1.3.6.1.4.1.9.9.82.1.2.1.1";

    leaf stpxPreferredVlansMap {
      type binary {
        length "128";
      }
      description
       "A string of octets containing one bit per VLAN in the
        management domain on this trunk port.  The first octet
        corresponds to VLANs with VlanIndex values of 0 through 7;
        the second octet to VLANs 8 through 15; etc.  The most
        significant bit of each octet corresponds to the lowest
        value VlanIndex in that octet.
        
        For each VLAN, if it is preferred on this trunk port, then
        the bit corresponding to that VLAN is set to '1'.
        The default value is 128 bytes of zeros.
        
        To avoid conflicts between overlapping partial updates by
        multiple managers, i.e., updates which modify only a portion
        of an instance of this object (e.g., enable/disable a single
        VLAN on the trunk port), any SNMP Set operation accessing an
        instance of this object should also write the value of
        vlanTrunkPortSetSerialNo.";
      smiv2:max-access "read-write";
      smiv2:oid "1.3.6.1.4.1.9.9.82.1.2.1.1.1";
    }

    leaf stpxPreferredVlansMap2k {
      type binary {
        length "0..128";
      }
      description
       "A string of octets containing one bit per VLAN for VLANS 
        with VlanIndex values of 1024 through 2047 in the management
        domain on this trunk port.  The first octet corresponds to 
        VLANs with VlanIndex values of 1024 through 1031; 
        the second octet to VLANs 1032 through 1039; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo.";
      smiv2:max-access "read-write";
      smiv2:oid "1.3.6.1.4.1.9.9.82.1.2.1.1.2";
    }

    leaf stpxPreferredVlansMap3k {
      type binary {
        length "0..128";
      }
      description
       "A string of octets containing one bit per VLAN for VLANS 
        with VlanIndex values of 2048 through 3071 in the management
        domain on this trunk port.  The first octet corresponds to 
        VLANs with VlanIndex values of 2048 through 2055; 
        the second octet to VLANs 2056 through 2063; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo.";
      smiv2:max-access "read-write";
      smiv2:oid "1.3.6.1.4.1.9.9.82.1.2.1.1.3";
    }

    leaf stpxPreferredVlansMap4k {
      type binary {
        length "0..128";
      }
      description
       "A string of octets containing one bit per VLAN for VLANS 
        with VlanIndex values of 3072 through 4095 in the management
        domain on this trunk port.  The first octet corresponds to 
        VLANs with VlanIndex values of 3072 through 3079; 
        the second octet to VLANs 3080 through 3087; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo.";
      smiv2:max-access "read-write";
      smiv2:oid "1.3.6.1.4.1.9.9.82.1.2.1.1.4";
    }
  }

  smiv2:alias "stpxLongStpPortPathCostTable" {
    description
     "A table containing the spanning tree port path cost
      configuration when stpxSpanningTreePathCostOperMode is
      long(2).
      
      If the value of stpxSpanningTreePathCostOperMode is 
      short(1), this table is not instantiated.";
    smiv2:oid "1.3.6.1.4.1.9.9.82.1.6.3";
  }

  smiv2:alias "stpxLongStpPortPathCostEntry" {
    description
     "A conceptual row containing the spanning tree port path cost
      configuration.";
    smiv2:oid "1.3.6.1.4.1.9.9.82.1.6.3.1";
  }

  augment "/bridge-mib:BRIDGE-MIB/bridge-mib:dot1dStpPortTable/bridge-mib:dot1dStpPortEntry" {
    description
     "A conceptual row containing the spanning tree port path cost
      configuration.";
    smiv2:oid "1.3.6.1.4.1.9.9.82.1.6.3.1";

    leaf stpxLongStpPortPathCost {
      type uint32;
      description
       "The contribution of this port to the path cost (in 32
        bits value) of paths towards the spanning tree root which
        include this port.
        
        This object is used to configure the spanning tree port
        path cost in 32 bits value range when the
        stpxSpanningTreePathCostOperMode is long(2).
        
        If the stpxSpanningTreePathCostOperMode is short(1), this 
        MIB object is not instantiated.";
      smiv2:max-access "read-write";
      smiv2:oid "1.3.6.1.4.1.9.9.82.1.6.3.1.1";
    }
  }

  smiv2:alias "stpxVlanMISTPInstMapTable" {
    description
     "A table containing the MISTP Instance Index of the VLANs for a
      particular management domain. 
      
      This table is only instantiated when the value of  
      stpxSpanningTreeType is mistp(2) or mistpPvstPlus(3).";
    smiv2:oid "1.3.6.1.4.1.9.9.82.1.7.3";
  }

  smiv2:alias "stpxVlanMISTPInstMapEntry" {
    description
     "A conceptual row containing the MISTP Instance Index of the 
      VLAN for a particular management domain.";
    smiv2:oid "1.3.6.1.4.1.9.9.82.1.7.3.1";
  }

  augment "/cisco-vtp:CISCO-VTP-MIB/cisco-vtp:vtpVlanTable/cisco-vtp:vtpVlanEntry" {
    description
     "A conceptual row containing the MISTP Instance Index of the 
      VLAN for a particular management domain.";
    smiv2:oid "1.3.6.1.4.1.9.9.82.1.7.3.1";

    leaf stpxVlanMISTPInstMapInstIndex {
      type int32 {
        range "0..256";
      }
      description
       "The MISTP instance, to which the corresponding vlan is mapped.
        If this value of this mib object is 0,  the corresponding vlan 
        is not configured to be mapped to any MISTP instance and all
        the ports under this VLAN remain in blocking state.";
      smiv2:max-access "read-only";
      smiv2:oid "1.3.6.1.4.1.9.9.82.1.7.3.1.1";
    }
  }

  smiv2:alias "stpxVlanMISTPInstMapEditTable" {
    description
     "A table containing the MISTP related information for the VLANs 
      in the Edit Buffers for a particular management domain.
      
      This table is only instantiated when when the value of
      stpxSpanningTreeType is mistp(2) or mistpPvstPlus(3).";
    smiv2:oid "1.3.6.1.4.1.9.9.82.1.7.4";
  }

  smiv2:alias "stpxVlanMISTPInstMapEditEntry" {
    description
     "Information about one VLAN mapping to one instance 
      in the Edit Buffer for a particular management domain.";
    smiv2:oid "1.3.6.1.4.1.9.9.82.1.7.4.1";
  }

  augment "/cisco-vtp:CISCO-VTP-MIB/cisco-vtp:vtpVlanEditTable/cisco-vtp:vtpVlanEditEntry" {
    description
     "Information about one VLAN mapping to one instance 
      in the Edit Buffer for a particular management domain.";
    smiv2:oid "1.3.6.1.4.1.9.9.82.1.7.4.1";

    leaf stpxVlanMISTPInstMapEditInstIndex {
      type int32 {
        range "0..256";
      }
      description
       "The MISTP instance, to which the corresponding vlan would be 
        mapped. The value of this mib object is from 0 to the value of
        stpxMISTPInstanceNumber. If setting the value of this object
        to 0, the corresponding vlan will not be mapped to a MISTP 
        instance and all the ports under this VLAN will be moved into
        the blocking state.";
      smiv2:max-access "read-write";
      smiv2:oid "1.3.6.1.4.1.9.9.82.1.7.4.1.1";
    }
  }

  smiv2:alias "stpxPreferredMISTPInstancesTable" {
    description
     "The table containing indications of which MISTP instances
      are preferred on which  trunk ports.  The preferred
      MISTP instances on a trunk port have a lower Path Cost value
      compared with the MISTP instances on the trunk not in the
      preferred list. 
      
      This table is only instantiated when the value of
      stpxSpanningTreeType is mistp(2) or mistpPvstPlus(3).";
    smiv2:oid "1.3.6.1.4.1.9.9.82.1.7.5";
  }

  smiv2:alias "stpxPreferredMISTPInstancesEntry" {
    description
     "An entry indicating which MISTP instances are preferred on
      a specific trunk port.";
    smiv2:oid "1.3.6.1.4.1.9.9.82.1.7.5.1";
  }

  augment "/cisco-vtp:CISCO-VTP-MIB/cisco-vtp:vlanTrunkPortTable/cisco-vtp:vlanTrunkPortEntry" {
    description
     "An entry indicating which MISTP instances are preferred on
      a specific trunk port.";
    smiv2:oid "1.3.6.1.4.1.9.9.82.1.7.5.1";

    leaf stpxPreferredMISTPInstancesMap {
      type binary {
        length "1..32";
      }
      description
       "A string of octets containing one bit per MISTP instances 
        in the management domain on this trunk port. The first octet
        corresponds to MISTP instances with InstIndex values of 1 
        through 8; the second octet to MISTP instances 9 through 16;
        etc. The most significant bit of each octet corresponds to 
        the lowest value instanceIndex in that octet. The number of 
        bits for this mib object will be determined by the value of 
        stpxMISTPInstanceNumber.
        
        For each instance, if it is preferred on this trunk port,
        then the bit corresponding to that instance is set to '1'.
        
        
        To avoid conflicts between overlapping partial updates by
        multiple managers, i.e., updates which modify only a portion
        of an instance of this object (e.g., enable/disable a single
        instance on the trunk port), any SNMP Set operation 
        accessing an instance of this object should also write the 
        value of vlanTrunkPortSetSerialNo.";
      smiv2:max-access "read-write";
      smiv2:oid "1.3.6.1.4.1.9.9.82.1.7.5.1.1";
    }
  }

  smiv2:alias "stpxPreferredMSTInstancesTable" {
    status deprecated;
    description
     "The table containing indications of which MST instances 
      are preferred on which  trunk ports.  The preferred
      MST instances on a trunk port have a lower Path Cost value
      compared with the MST instances on the trunk not in the
      preferred list.";
    smiv2:oid "1.3.6.1.4.1.9.9.82.1.11.10";
  }

  smiv2:alias "stpxPreferredMSTInstancesEntry" {
    status deprecated;
    description
     "An entry indicating which MST instances are preferred on 
      a specific trunk port.";
    smiv2:oid "1.3.6.1.4.1.9.9.82.1.11.10.1";
  }

  augment "/cisco-vtp:CISCO-VTP-MIB/cisco-vtp:vlanTrunkPortTable/cisco-vtp:vlanTrunkPortEntry" {
    status deprecated;
    description
     "An entry indicating which MST instances are preferred on 
      a specific trunk port.";
    smiv2:oid "1.3.6.1.4.1.9.9.82.1.11.10.1";

    leaf stpxPreferredMSTInstancesMap {
      type binary {
        length "1..32";
      }
      status deprecated;
      description
       "A string of octets containing one bit per MST instances 
        on this trunk port.  The first octet corresponds to MST 
        instances of 0 through 7; the second octet to MST instances 
        8 through 15; etc. The most significant bit of each octet 
        corresponds to the lowest MST instance value in that octet. 
        The number of bits for this mib object will be determined 
        by the value of stpxMSTMaxInstanceNumber.
        
        For each instance, if it is preferred on this trunk port, 
        then the bit corresponding to that instance is set to '1'.";
      smiv2:max-access "read-write";
      smiv2:oid "1.3.6.1.4.1.9.9.82.1.11.10.1.1";
    }
  }

  notification stpxInconsistencyUpdate {
    description
     "A stpxPortInconsistencyUpdate notification is sent by a
      bridge when an instance of stpxInconsistentState is 
      created or destroyed.  That is, when an inconsistency is
      discovered in the VLAN's Spanning Tree for a particular 
      port, or when such an inconsistency disappears.  Note 
      that the trap is not sent if the port transitions between
      different types of inconsistency.
      
      The stpxInconsistentState value indicates the type of
      inconsistency which now exists/no longer exists for the 
      relevant VLAN on the relevant port.";
    smiv2:oid "1.3.6.1.4.1.9.9.82.2.0.1";

    container object-1 {

      leaf stpxVlanIndex {
        type leafref {
          path "/CISCO-STP-EXTENSIONS-MIB:CISCO-STP-EXTENSIONS-MIB/CISCO-STP-EXTENSIONS-MIB:stpxInconsistencyTable/CISCO-STP-EXTENSIONS-MIB:stpxInconsistencyEntry/CISCO-STP-EXTENSIONS-MIB:stpxVlanIndex";
        }
      }

      leaf stpxPortIndex {
        type leafref {
          path "/CISCO-STP-EXTENSIONS-MIB:CISCO-STP-EXTENSIONS-MIB/CISCO-STP-EXTENSIONS-MIB:stpxInconsistencyTable/CISCO-STP-EXTENSIONS-MIB:stpxInconsistencyEntry/CISCO-STP-EXTENSIONS-MIB:stpxPortIndex";
        }
      }

      leaf stpxInconsistentState {
        type leafref {
          path "/CISCO-STP-EXTENSIONS-MIB:CISCO-STP-EXTENSIONS-MIB/CISCO-STP-EXTENSIONS-MIB:stpxInconsistencyTable/CISCO-STP-EXTENSIONS-MIB:stpxInconsistencyEntry/CISCO-STP-EXTENSIONS-MIB:stpxInconsistentState";
        }
      }
    }
  }

  notification stpxRootInconsistencyUpdate {
    description
     "A stpxRootInconsistencyUpdate notification is sent by a
      bridge when an instance of stpxRootInconsistencyState
      is created or destroyed. That is, when an
      root-inconsistency is discovered in the VLAN's or 
      instance's Spanning Tree for a particular port, or when 
      such an root-inconsistency disappears. For creation, the 
      value of stpxRootInconsistencyState in the notification is
      true(1); for deletion, the value is false(2).
      
      The object value of stpxSpanningTreeType indicates
      which Spanning Tree protocol is running when an instance 
      of stpxRootInconsistencyState is created or destroyed.  ";
    smiv2:oid "1.3.6.1.4.1.9.9.82.2.0.2";

    container object-1 {

      leaf stpxRootInconsistencyIndex {
        type leafref {
          path "/CISCO-STP-EXTENSIONS-MIB:CISCO-STP-EXTENSIONS-MIB/CISCO-STP-EXTENSIONS-MIB:stpxRootInconsistencyTable/CISCO-STP-EXTENSIONS-MIB:stpxRootInconsistencyEntry/CISCO-STP-EXTENSIONS-MIB:stpxRootInconsistencyIndex";
        }
      }

      leaf stpxRootInconsistencyPortIndex {
        type leafref {
          path "/CISCO-STP-EXTENSIONS-MIB:CISCO-STP-EXTENSIONS-MIB/CISCO-STP-EXTENSIONS-MIB:stpxRootInconsistencyTable/CISCO-STP-EXTENSIONS-MIB:stpxRootInconsistencyEntry/CISCO-STP-EXTENSIONS-MIB:stpxRootInconsistencyPortIndex";
        }
      }

      leaf stpxRootInconsistencyState {
        type leafref {
          path "/CISCO-STP-EXTENSIONS-MIB:CISCO-STP-EXTENSIONS-MIB/CISCO-STP-EXTENSIONS-MIB:stpxRootInconsistencyTable/CISCO-STP-EXTENSIONS-MIB:stpxRootInconsistencyEntry/CISCO-STP-EXTENSIONS-MIB:stpxRootInconsistencyState";
        }
      }
    }

    container object-2 {

      leaf stpxSpanningTreeType {
        type leafref {
          path "/CISCO-STP-EXTENSIONS-MIB:CISCO-STP-EXTENSIONS-MIB/CISCO-STP-EXTENSIONS-MIB:stpxSpanningTreeObjects/CISCO-STP-EXTENSIONS-MIB:stpxSpanningTreeType";
        }
      }
    }
  }

  notification stpxLoopInconsistencyUpdate {
    description
     "A stpxLoopInconsistencyUpdate notification is sent by a
      bridge when an instance of stpxLoopInconsistencyState
      is created or destroyed. That is, when an
      loop-inconsistency is discovered in the VLAN's or 
      instance's Spanning Tree for a particular port, or when 
      such an loop-inconsistency disappears. For creation, 
      the value of stpxLoopInconsistencyState in the 
      notification is true(1); for deletion, the value is 
      false(2).
      
      The object value of stpxSpanningTreeType indicates
      which Spanning Tree protocol is running when an instance
      of stpxLoopInconsistencyState is created or 
      destroyed.";
    smiv2:oid "1.3.6.1.4.1.9.9.82.2.0.3";

    container object-1 {

      leaf stpxLoopInconsistencyIndex {
        type leafref {
          path "/CISCO-STP-EXTENSIONS-MIB:CISCO-STP-EXTENSIONS-MIB/CISCO-STP-EXTENSIONS-MIB:stpxLoopInconsistencyTable/CISCO-STP-EXTENSIONS-MIB:stpxLoopInconsistencyEntry/CISCO-STP-EXTENSIONS-MIB:stpxLoopInconsistencyIndex";
        }
      }

      leaf stpxLoopInconsistencyPortIndex {
        type leafref {
          path "/CISCO-STP-EXTENSIONS-MIB:CISCO-STP-EXTENSIONS-MIB/CISCO-STP-EXTENSIONS-MIB:stpxLoopInconsistencyTable/CISCO-STP-EXTENSIONS-MIB:stpxLoopInconsistencyEntry/CISCO-STP-EXTENSIONS-MIB:stpxLoopInconsistencyPortIndex";
        }
      }

      leaf stpxLoopInconsistencyState {
        type leafref {
          path "/CISCO-STP-EXTENSIONS-MIB:CISCO-STP-EXTENSIONS-MIB/CISCO-STP-EXTENSIONS-MIB:stpxLoopInconsistencyTable/CISCO-STP-EXTENSIONS-MIB:stpxLoopInconsistencyEntry/CISCO-STP-EXTENSIONS-MIB:stpxLoopInconsistencyState";
        }
      }
    }

    container object-2 {

      leaf stpxSpanningTreeType {
        type leafref {
          path "/CISCO-STP-EXTENSIONS-MIB:CISCO-STP-EXTENSIONS-MIB/CISCO-STP-EXTENSIONS-MIB:stpxSpanningTreeObjects/CISCO-STP-EXTENSIONS-MIB:stpxSpanningTreeType";
        }
      }
    }
  }

  smiv2:alias "ciscoStpExtensionsMIB" {
    smiv2:oid "1.3.6.1.4.1.9.9.82";
  }

  smiv2:alias "stpxObjects" {
    smiv2:oid "1.3.6.1.4.1.9.9.82.1";
  }

  smiv2:alias "stpxUplinkFastObjects" {
    smiv2:oid "1.3.6.1.4.1.9.9.82.1.1";
  }

  smiv2:alias "stpxVlanObjects" {
    smiv2:oid "1.3.6.1.4.1.9.9.82.1.2";
  }

  smiv2:alias "stpxInconsistencyObjects" {
    smiv2:oid "1.3.6.1.4.1.9.9.82.1.3";
  }

  smiv2:alias "stpxBackboneFastObjects" {
    smiv2:oid "1.3.6.1.4.1.9.9.82.1.4";
  }

  smiv2:alias "stpxRootGuardObjects" {
    smiv2:oid "1.3.6.1.4.1.9.9.82.1.5";
  }

  smiv2:alias "stpxSpanningTreeObjects" {
    smiv2:oid "1.3.6.1.4.1.9.9.82.1.6";
  }

  smiv2:alias "stpxMISTPObjects" {
    smiv2:oid "1.3.6.1.4.1.9.9.82.1.7";
  }

  smiv2:alias "stpxLoopGuardObjects" {
    smiv2:oid "1.3.6.1.4.1.9.9.82.1.8";
  }

  smiv2:alias "stpxFastStartObjects" {
    smiv2:oid "1.3.6.1.4.1.9.9.82.1.9";
  }

  smiv2:alias "stpxBpduSkewingObjects" {
    smiv2:oid "1.3.6.1.4.1.9.9.82.1.10";
  }

  smiv2:alias "stpxMSTObjects" {
    smiv2:oid "1.3.6.1.4.1.9.9.82.1.11";
  }

  smiv2:alias "stpxRSTPObjects" {
    smiv2:oid "1.3.6.1.4.1.9.9.82.1.12";
  }

  smiv2:alias "stpxRPVSTObjects" {
    smiv2:oid "1.3.6.1.4.1.9.9.82.1.13";
  }

  smiv2:alias "stpxSMSTObjects" {
    smiv2:oid "1.3.6.1.4.1.9.9.82.1.14";
  }

  smiv2:alias "stpxNotifications" {
    smiv2:oid "1.3.6.1.4.1.9.9.82.2";
  }

  smiv2:alias "stpxNotificationsPrefix" {
    smiv2:oid "1.3.6.1.4.1.9.9.82.2.0";
  }

  smiv2:alias "stpxMIBConformance" {
    smiv2:oid "1.3.6.1.4.1.9.9.82.3";
  }

  smiv2:alias "stpxMIBCompliances" {
    smiv2:oid "1.3.6.1.4.1.9.9.82.3.1";
  }

  smiv2:alias "stpxMIBGroups" {
    smiv2:oid "1.3.6.1.4.1.9.9.82.3.2";
  }

}
