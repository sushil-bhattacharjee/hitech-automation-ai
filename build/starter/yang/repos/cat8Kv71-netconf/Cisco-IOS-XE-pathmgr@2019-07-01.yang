module Cisco-IOS-XE-pathmgr {
  namespace "http://cisco.com/ns/yang/Cisco-IOS-XE-pathmgr";
  prefix ios-pathmgr;

  import cisco-semver {
    prefix cisco-semver;
  }
  import ietf-inet-types {
    prefix inet;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Path Manager Yang model.
     Copyright (c) 2016 by Cisco Systems, Inc.
     All rights reserved.";

  revision 2019-07-01 {
    description
      "Establish semantic version baseline";
    cisco-semver:module-version "1.0.0";
  }
  revision 2017-02-07 {
    description
      "Initial revision";
  }

  grouping config-pm-agent-instance-grouping {
    container enterprise-prefix {
      description
        "Enterprise prefix configuration";
      container ipv4 {
        description
          "IPv4 enterprise prefix-list";
        leaf prefix-list {
          description
            "Specify prefix-list with static site targets";
          type string;
        }
      }
      container ipv6 {
        description
          "IPv6 enterprise prefix-list";
        leaf prefix-list {
          description
            "Specify prefix-list with static site targets";
          type string;
        }
      }
    }
  }

  grouping config-pm-agent-grouping {
    container pm-agent {
      description
        "pm-agent Configuration Commands";
      presence "true";
      container config-pm-agent {
        container device {
          description
            "Enter the device ID";
          container id {
            description
              "Specify the device ID";
            list device_range {
              key "device_id_range";
              leaf device_id_range {
                description
                  "Specify the device-id value";
                type uint32 {
                  range "1..65535";
                }
              }
              leaf name {
                description
                  "Specify the device name";
                type string;
              }
            }
          }
          container type {
            description
              "Enter the device type";
            container ntr {
              description
                "ntr device type";
              presence "true";
              container rtr {
                description
                  "rtr device type";
                presence "true";
                leaf xtr {
                  description
                    "xtr device type";
                  type empty;
                }
              }
              container xtr {
                description
                  "xtr device type";
                presence "true";
                leaf rtr {
                  description
                    "rtr device type";
                  type empty;
                }
              }
            }
            leaf pxtr {
              description
                "pxtr device type";
              type empty;
            }
            container rtr {
              description
                "rtr device type";
              presence "true";
              leaf ntr {
                description
                  "ntr device type";
                type empty;
              }
              container xtr {
                description
                  "xtr device type";
                presence "true";
                leaf ntr {
                  description
                    "ntr device type";
                  type empty;
                }
              }
            }
            container xtr {
              description
                "xtr device type";
              presence "true";
              leaf ntr {
                description
                  "ntr device type";
                type empty;
              }
              leaf rtr {
                description
                  "rtr device type";
                type empty;
              }
            }
          }
        }
        list instance-id {
          description
            "Enter the instance ID";
          key "instance_id_range";
          leaf instance_id_range {
            description
              "Specify the instance-id value";
            type uint32 {
              range "0..65535";
            }
          }
          container config-pm-agent-instance {
            uses config-pm-agent-instance-grouping;
          }
        }
        container region {
          description
            "Enter the region ID";
          container id {
            description
              "Specify the region ID";
            list region_id_range {
              key "region_id_range";
              leaf region_id_range {
                description
                  "Specify the region-id value";
                type uint32 {
                  range "1..4294967295";
                }
              }
              leaf name {
                description
                  "Specify the region name";
                type string;
              }
            }
          }
        }
        leaf shutdown {
          description
            "shut the device";
          type empty;
        }
        container site {
          description
            "Enter the site configuration";
          container id {
            description
              "Specify the site ID";
            list site_id_range {
              key "site_id_range";
              leaf site_id_range {
                description
                  "Specify the site-id value";
                type uint32 {
                  range "1..4294967295";
                }
              }
              leaf name {
                description
                  "Specify the site name";
                type string;
              }
            }
          }
        }
        container tenant {
          description
            "enter the tenant configuration";
          container id {
            description
              "specify the tenant id";
            list tenant_id_range {
              key "tenant_id_range";
              leaf tenant_id_range {
                description
                  "specify the tenant-id value";
                type uint32 {
                  range "1..4294967295";
                }
              }
              leaf name {
                description
                  "specify the tenant name";
                type string;
              }
            }
          }
        }
        container pmcs {
          description
            "Enter the pmcs configuration";
          container ipv4 {
            description
              "Enter the IPv4 address";
            list pmcs_ipv4 {
              key "ipv4";
              leaf ipv4 {
                description
                  "IPv4 pmcs address e.g 10.10.0.0";
                type inet:ipv4-address;
              }
              leaf backup {
                description
                  "set ipv4/ipv6 address as backup";
                type empty;
              }
              container ipv6 {
                description
                  "Enter the IPv6 address";
                list pmcs_ipv6 {
                  key "ipv6";
                  leaf ipv6 {
                    description
                      "IPv6 pmcs Addr, e.g abcd:1234";
                    type inet:ipv6-address;
                  }
                  leaf backup {
                    description
                      "set ipv4/ipv6 address as backup";
                    type empty;
                  }
                }
              }
            }
          }
          container ipv6 {
            description
              "Enter the IPv6 address";
            list ipv6 {
              key "ipv6";
              leaf ipv6 {
                description
                  "IPv6 pmcs Addr, e.g abcd:1234";
                type inet:ipv6-address;
              }
              leaf backup {
                description
                  "set ipv4/ipv6 address as backup";
                type empty;
              }
              leaf ipv4 {
                description
                  "IPv4 pmcs address e.g 10.10.0.0";
                type inet:ipv4-address;
              }
            }
          }
        }
      }
    }
  }

  augment "/ios:native" {
    uses config-pm-agent-grouping;
  }
}
