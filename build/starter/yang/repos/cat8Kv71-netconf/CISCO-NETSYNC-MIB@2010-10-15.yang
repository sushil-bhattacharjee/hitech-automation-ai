/*
 * Generated by confdc --mib2yang-std
 * Source: mgmt/dmi/model/mib/src/patched/CISCO-NETSYNC-MIB.mib
 */
/*
 * This YANG module has been generated by smidump 0.5.0:
 *
 *      smidump -f yang CISCO-NETSYNC-MIB
 *
 * Do not edit. Edit the source file instead!
 */

module CISCO-NETSYNC-MIB {

  namespace "urn:ietf:params:xml:ns:yang:smiv2:CISCO-NETSYNC-MIB";
  prefix CISCO-NETSYNC-MIB;

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    
    Postal: 170 W Tasman Drive
    
    San Jose, CA  95134
    
    USA
    
    
    Tel: +1 800 553-NETS
    
    
    E-mail: cs-sync-e@cisco.com";

  description
   "The Synchronous Ethernet (SyncE) MIB is defined
    for monitoring network synchronization based on
    ITU-T G.781 clock selection.
    
    Synchronous Ethernet (SyncE) is a standard defined
    for delivering timing to the remote NEs through a 
    Packet Network.   SyncE is well defined by ITU-T
    which included G.8261, G.8262, G.8264 and G.781.
    It leverages the PHY layer of Ethernet to transmit
    frequency to the remote sites.  Its functionality
    and accuracy mimics that of the SONET/SDH network
    because of its physical layer characteristic.
    In order to allow best clock source traceabiliy,
    correctly define the timing source and helps
    preventing timing loop, Synchronization Status
    Message is required for SyncE.  This is similar
    to SONET/SDH.  However, since SONET/SDH use 4 bits
    from the two S bytes in the SONET/SDH overhead
    frame for such message, Ethernet relies on a
    different channel called ESMC (Ethernet
    Synchronization Messaging Channel) which is based
    on IEEE 802.3 Organization Specific Slow Protocol.
    
    Glossary:
    AIS: Alarm Indication Signal
    ATM: Asynchronous Transfer Mode
    EEC: Ethernet Equipment Clock
    ESMC: Ethernet Synchronization Messaging Channel
    QL: Quality Level
    SASE: Stand Alone Synchronization Equipment
    SSM: Synchronization Status Messaging";

  revision 2010-10-15 {
    description
     "Initial version of the SyncE MIB module.";
  }

  typedef CiscoNetsyncIfType {
    type enumeration {
      enum "netsyncIfTypeUnknown" {
        value "1";
      }
      enum "netsyncIfTypeInternal" {
        value "2";
      }
      enum "netsyncIfTypeEthernet" {
        value "3";
      }
      enum "netsyncIfTypeSonet" {
        value "4";
      }
      enum "netsyncIfTypeTop" {
        value "5";
      }
      enum "netsyncIfTypeExt" {
        value "6";
      }
      enum "netsyncIfTypeController" {
        value "7";
      }
      enum "netsyncIfTypeGps" {
        value "8";
      }
      enum "netsyncIfTypeAtm" {
        value "9";
      }
    }
    description
     "Network synchronization clock source Interface type.
      
      Netsync interface         Interface type
      ========================  ==============
      netsyncIfTypeUnknown      Unknown
      netsyncIfTypeInternal     Internal
      netsyncIfTypeEthernet     Ethernet
      netsyncIfTypeSonet        SONET
      netsyncIfTypeTop          Timing Over Packet
      netsyncIfTypeExt          External interface
      netsyncIfTypeController   T1/E1 Controller
      netsyncIfTypeGps          GPS
      netsyncIfTypeAtm          ATM
      
      For external and GPS interface types, the following
      syntax is used for specifying an interface:
          <slot>/<card>/<port> <signal type> where
      slot : slot number of the device where card is present.
      card : bay number in which card is inserted.
      port : port number on the card.
      signal type: hardware signal of the specified
                   <slot>/<card>/<port>. Examples of signal
                   type are T1 SF and T1 ESF.";
  }

  typedef CiscoNetsyncNetworkOption {
    type enumeration {
      enum "netsyncNetworkOptionUnknown" {
        value "1";
      }
      enum "netsyncNetworkOption1" {
        value "2";
      }
      enum "netsyncNetworkOption2Gen1" {
        value "3";
      }
      enum "netsyncNetworkOption2Gen2" {
        value "4";
      }
      enum "netsyncNetworkOption3" {
        value "5";
      }
      enum "netsyncNetworkOptionInvalid" {
        value "6";
      }
    }
    description
     "Network synchronization networking options.
      
      Network option                Network option type
      ===========================   ===================
      netsyncNetworkOptionUnknown   Unknown network option
      netsyncNetworkOption1         Option I
      netsyncNetworkOption2Gen1     Option II Generation 1
      netsyncNetworkOption2Gen2     Option II Generation 2
      netsyncNetworkOption3         Option III
      netsyncNetworkOptionInvalid   Invalid network option
      
      Option I refers to ITU-T Option I synchronization networks.
      
      Option II refers to ITU-T Option II synchronization networks
      designed for North America.
      
      Option III refers to ITU-T Option III synchronization networks
      designed for Japan.";
    reference
     "ITU-T standard G.781";
  }

  typedef CiscoNetsyncEECOption {
    type enumeration {
      enum "netsyncEECOptionUnknown" {
        value "1";
      }
      enum "netsyncEECOption1" {
        value "2";
      }
      enum "netsyncEECOption2" {
        value "3";
      }
      enum "netsyncEECOptionInvalid" {
        value "4";
      }
    }
    description
     "Network synchronization EEC (Ethernet Equipment Clock)
      options.
      
      The EEC options are for Synchronous Ethernet devices and define
      the requirements for clocks, e.g. bandwidth, frequency accuracy,
      holdover and noise generation.
      
      Two options are defined:
      EEC-Option 1: Designed to interwork with network optimized for
      the 2048 kbit/s hierarchy.
      
      EEC-Option 2: Designed to interwork with network optimized for
      the 1544 kbit/s hierarchy.
      
      netsyncEECOptionUnknown   Unknown
      netsyncEECOption1         EEC option 1
      netsyncEECOption2         EEC option 2
      netsyncEECOptionInvalid   Invalid EEC option";
    reference
     "ITU-T standard G.781";
  }

  typedef CiscoNetsyncQLMode {
    type enumeration {
      enum "netsyncQLModeUnknown" {
        value "1";
      }
      enum "netsyncQLModeQlDisabled" {
        value "2";
      }
      enum "netsyncQLModeQlEnabled" {
        value "3";
      }
    }
    description
     "The clock mode of the network synchronization clock selection
      process as described in ITU-T standard G.781 section 5.12.
      
      G.781 clock selection runs in one of two clock modes:
      QL (Quality Level) enabled mode and QL disabled mode.  
      
      netsyncQLModeUnknown    - QL mode unknown
      netsyncQLModeQlDisabled - QL-disabled mode;
                                clock selection is running 
                                in QL disabled mode,
                                which primarily considers
                                the source's priority as the
                                clock selection criteria.
      netsyncQLModeQlEnabled  - QL-enabled mode
                                clock selection is running
                                in QL enabled mode,
                                which primarily considers
                                the source's clock quality
                                level and priority as the
                                clock selection criteria.";
    reference
     "ITU-T standard G.781 section 5.12";
  }

  typedef CiscoNetsyncClockMode {
    type enumeration {
      enum "netsyncClockModeUnknown" {
        value "1";
      }
      enum "netsyncClockModeFreerun" {
        value "2";
      }
      enum "netsyncClockModeHoldover" {
        value "3";
      }
      enum "netsyncClockModeLocked" {
        value "4";
      }
    }
    description
     "Clock operating mode:
      
      netsyncClockModeUnknown  - system is unable to 
                                 determine the operating mode.
      netsyncClockModeFreerun  - free-running mode.
      netsyncClockModeHoldover - holdover mode.
      netsyncClockModeLocked   - a valid clock source is locked.";
  }

  typedef CiscoNetsyncQualityLevel {
    type enumeration {
      enum "netsyncQualityLevelNULL" {
        value "1";
      }
      enum "netsyncQualityLevelDNU" {
        value "2";
      }
      enum "netsyncQualityLevelDUS" {
        value "3";
      }
      enum "netsyncQualityLevelFAILED" {
        value "4";
      }
      enum "netsyncQualityLevelINV0" {
        value "5";
      }
      enum "netsyncQualityLevelINV1" {
        value "6";
      }
      enum "netsyncQualityLevelINV2" {
        value "7";
      }
      enum "netsyncQualityLevelINV3" {
        value "8";
      }
      enum "netsyncQualityLevelINV4" {
        value "9";
      }
      enum "netsyncQualityLevelINV5" {
        value "10";
      }
      enum "netsyncQualityLevelINV6" {
        value "11";
      }
      enum "netsyncQualityLevelINV7" {
        value "12";
      }
      enum "netsyncQualityLevelINV8" {
        value "13";
      }
      enum "netsyncQualityLevelINV9" {
        value "14";
      }
      enum "netsyncQualityLevelINV10" {
        value "15";
      }
      enum "netsyncQualityLevelINV11" {
        value "16";
      }
      enum "netsyncQualityLevelINV12" {
        value "17";
      }
      enum "netsyncQualityLevelINV13" {
        value "18";
      }
      enum "netsyncQualityLevelINV14" {
        value "19";
      }
      enum "netsyncQualityLevelINV15" {
        value "20";
      }
      enum "netsyncQualityLevelNSUPP" {
        value "21";
      }
      enum "netsyncQualityLevelPRC" {
        value "22";
      }
      enum "netsyncQualityLevelPROV" {
        value "23";
      }
      enum "netsyncQualityLevelPRS" {
        value "24";
      }
      enum "netsyncQualityLevelSEC" {
        value "25";
      }
      enum "netsyncQualityLevelSMC" {
        value "26";
      }
      enum "netsyncQualityLevelSSUA" {
        value "27";
      }
      enum "netsyncQualityLevelSSUB" {
        value "28";
      }
      enum "netsyncQualityLevelST2" {
        value "29";
      }
      enum "netsyncQualityLevelST3" {
        value "30";
      }
      enum "netsyncQualityLevelST3E" {
        value "31";
      }
      enum "netsyncQualityLevelST4" {
        value "32";
      }
      enum "netsyncQualityLevelSTU" {
        value "33";
      }
      enum "netsyncQualityLevelTNC" {
        value "34";
      }
      enum "netsyncQualityLevelUNC" {
        value "35";
      }
      enum "netsyncQualityLevelUNK" {
        value "36";
      }
    }
    description
     "Clock source QL (quality level) is defined in ITU-T G.781
      section 5.4 to reflect the synchronization quality within a
      network Option, i.e. I, II, and III.
      
      The following clock source quality levels are defined for the
      synchronization process of Option I: 
      
      QL-PRC     Primary reference clock 
      QL-SSU-A   Type I or V slave clock defined in ITU-T G.811
      QL-SSU-B   Type VI slave clock defined in ITU-T G.812
      QL-SEC     Synchronous equipment clock
      QL-DNU     Do not use for synchronization
      QL-INVx    Unallocated SSM value,
                 where x represent the value of SSM received
      QL-FAILED  Signal failure state
      QL-UNC     Unconnected to an input
      QL-NSUPP   Not supporting the SSM processing
      
      The following clock source quality levels are defined for the
      synchronization process of Option II: 
      
      QL-PRS     PRS traceable
      QL-STU     Synchronized; traceability unknown
      QL-ST2     Stratum 2
      QL-TNC     Transit node clock
      QL-ST3E    Stratum 3E
      QL-ST3     Stratum 3
      QL-SMC     SONET clock self timed
      QL-ST4     Stratum 4 freerun
      QL-PROV    Provisionable by the network operator
      QL-DUS     Do not use for synchronization
      QL-INVx    Unallocated SSM value,
                 where x represent the value of SSM received
      QL-FAILED  Signal failure state
      QL-UNC     Unconnected to an input
      QL-NSUPP   Not supporting the SSM processing
      
      The following clock source quality levels are defined for the
      synchronization process of Option III:
      
      QL-UNK     Unknown clock source
      QL-SEC     Synchronous equipment clock
      
      QL-INVx    Unallocated SSM value,
                 where x represent the value of SSM received
      QL-FAILED  Signal failure state
      QL-UNC     Unconnected to an input
      QL-NSUPP   Not supporting the SSM processing        ";
    reference
     "ITU-T standard G.781 section 5.4";
  }

  typedef CiscoNetsyncSSMCap {
    type enumeration {
      enum "netsyncSSMCapNone" {
        value "1";
      }
      enum "netsyncSSMCapTxRx" {
        value "2";
      }
      enum "netsyncSSMCapTx" {
        value "3";
      }
      enum "netsyncSSMCapRx" {
        value "4";
      }
      enum "netsyncSSMCapInvalid" {
        value "5";
      }
    }
    description
     "Network synchronization clock source interface SSM
      (Synchronization Status Message) capability.
      
      SSM Capability         Capability information
      =====================  ======================
      netsyncSSMCapNone      No SSM capability
      netsyncSSMCapTxRx      To transmit and receive SSM
      netsyncSSMCapTx        To transmit SSM only
      netsyncSSMCapRx        To receive SSM only
      netsyncSSMCapInvalid   Capability invalid or unsupported";
  }

  typedef CiscoNetsyncESMCCap {
    type enumeration {
      enum "netsyncESMCCapNone" {
        value "1";
      }
      enum "netsyncESMCCapTxRx" {
        value "2";
      }
      enum "netsyncESMCCapTx" {
        value "3";
      }
      enum "netsyncESMCCapRx" {
        value "4";
      }
      enum "netsyncESMCCapInvalid" {
        value "5";
      }
    }
    description
     "Network synchronization clock source interface ESMC
      (Ethernet Synchronization Messaging Channel)
      capability.
      
      ESMC Capability         Capability information
      ======================  ======================
      netsyncESMCCapNone      No ESMC capability
      netsyncESMCCapTxRx      To transmit and receive ESMC
      netsyncESMCCapTx        To transmit SSM only
      netsyncESMCCapRx        To receive SSM only
      netsyncESMCCapInvalid   Capability invalid or unsupported";
  }

  typedef CiscoNetsyncAlarmInfo {
    type bits {
      bit netsyncSrcAlarmReasonAIS {
        position "0";
      }
      bit netsyncSrcAlarmReasonOOR {
        position "1";
      }
      bit netsyncSrcAlarmReasonOIR {
        position "2";
      }
      bit netsyncSrcAlarmReasonInternal {
        position "3";
      }
    }
    description
     "Input clock source's alarm reasons:
      
      netsyncSrcAlarmReasonAIS      - Alarm Indication Signal
      netsyncSrcAlarmReasonOOR      - Out of range
      netsyncSrcAlarmReasonOIR      - Online Insertion Removal
      netsyncSrcAlarmReasonInternal - Internal";
  }


  container CISCO-NETSYNC-MIB {
    config false;

    container ciscoNetsyncMIBNotifControl {
      smiv2:oid "1.3.6.1.4.1.9.9.761.1.3";

      leaf cnsMIBEnableStatusNotification {
        type boolean;
        description
         "A control object to enable/disable
          ciscoNetsyncSelectedT0Clock, ciscoNetsyncSelectedT4Clock,
          ciscoNetsyncInputSignalFailureStatus,
          ciscoNetsyncInputAlarmStatus notifications at the system
          level.
          This object should hold any of the below values.
              true - The notif is enabled globally for the system
              false- The notif is disabled globally for the system";
        smiv2:defval "false";
        smiv2:max-access "read-write";
        smiv2:oid "1.3.6.1.4.1.9.9.761.1.3.1";
      }
    }

    container cnsClkSelGlobalTable {
      description
       "G.781 clock selection process table.
        This table contains the global parameters for the G.781 clock
        selection process.";
      smiv2:oid "1.3.6.1.4.1.9.9.761.1.1.1";

      list cnsClkSelGlobalEntry {
        key "cnsClkSelGloProcIndex";
        description
         "An entry is added to cnsClkSelGlobalTable when G.781 clock
          selection is enabled in the device configuration.  The entry
          is removed when G.781 clock selection is removed from the
          configuration.";
        smiv2:oid "1.3.6.1.4.1.9.9.761.1.1.1.1";

        leaf cnsClkSelGloProcIndex {
          type uint32 {
            range "0..4294967295";
          }
          description
           "An index that uniquely represents a clock selection process.
            
            This index is assigned arbitrarily by the system
            and may not be persistent across reboots.";
          smiv2:max-access "not-accessible";
          smiv2:oid "1.3.6.1.4.1.9.9.761.1.1.1.1.1";
        }

        leaf cnsClkSelGlobProcessMode {
          type CISCO-NETSYNC-MIB:CiscoNetsyncQLMode;
          description
           "This object indicates the QL mode of
            the network synchronization clock selection
            process as described in ITU-T standard G.781
            section 5.12.";
          smiv2:max-access "read-only";
          smiv2:oid "1.3.6.1.4.1.9.9.761.1.1.1.1.2";
        }

        leaf cnsClkSelGlobClockMode {
          type CISCO-NETSYNC-MIB:CiscoNetsyncClockMode;
          description
           "This object indicates the operating mode
            of the system clock.";
          smiv2:max-access "read-only";
          smiv2:oid "1.3.6.1.4.1.9.9.761.1.1.1.1.3";
        }

        leaf cnsClkSelGlobNetsyncEnable {
          type boolean;
          description
           "This object indicates whether the G.781
            clock selection is enabled or not.
            
            'true'  - G.781 clock selection is enabled
            'false' - G.781 clock selection is disabled";
          smiv2:defval "false";
          smiv2:max-access "read-only";
          smiv2:oid "1.3.6.1.4.1.9.9.761.1.1.1.1.4";
        }

        leaf cnsClkSelGlobRevertiveMode {
          type boolean;
          description
           "This object indicates the revertive mode
            setting in the G.781 clock selection process.
            
            The switching of clock sources can be made revertive or
            non-revertive. In non-revertive mode, an alternate
            clock source is maintained even after the original clock
            source has recovered from the failure that caused the switch.
            In revertive mode, the clock selection process switches back
            to the original clock source after recovering from the
            failure.";
          smiv2:defval "false";
          smiv2:max-access "read-only";
          smiv2:oid "1.3.6.1.4.1.9.9.761.1.1.1.1.5";
        }

        leaf cnsClkSelGlobESMCMode {
          type boolean;
          description
           "This object indicates if global ESMC is enabled.
            With ESMC enabled globally, the system is capable
            of handling ESMC messages.";
          smiv2:defval "false";
          smiv2:max-access "read-only";
          smiv2:oid "1.3.6.1.4.1.9.9.761.1.1.1.1.6";
        }

        leaf cnsClkSelGlobEECOption {
          type CISCO-NETSYNC-MIB:CiscoNetsyncEECOption;
          description
           "This object indicates the network synchronization
            EEC (Ethernet Equipment Clock) option.";
          reference
           "ITU-T standard G.781";
          smiv2:defval "netsyncEECOptionUnknown";
          smiv2:max-access "read-only";
          smiv2:oid "1.3.6.1.4.1.9.9.761.1.1.1.1.7";
        }

        leaf cnsClkSelGlobNetworkOption {
          type CISCO-NETSYNC-MIB:CiscoNetsyncNetworkOption;
          description
           "This object indicates the synchronization
            network option.";
          reference
           "ITU-T standard G.781";
          smiv2:defval "netsyncNetworkOptionUnknown";
          smiv2:max-access "read-only";
          smiv2:oid "1.3.6.1.4.1.9.9.761.1.1.1.1.8";
        }

        leaf cnsClkSelGlobHoldoffTime {
          type uint32 {
            range "0..4294967295";
          }
          units "milliseconds";
          description
           "This object indicates the global
            holdoff time in the G.781 clock
            selection process.";
          reference
           "ITU-T standard G.781 section 5.8";
          smiv2:defval "300";
          smiv2:max-access "read-only";
          smiv2:oid "1.3.6.1.4.1.9.9.761.1.1.1.1.9";
        }

        leaf cnsClkSelGlobWtrTime {
          type uint32 {
            range "0..4294967295";
          }
          units "seconds";
          description
           "This object indicates the global
            wait-to-restore time in the G.781
            clock selection process.";
          reference
           "ITU-T standard G.781 section 5.9";
          smiv2:defval "300";
          smiv2:max-access "read-only";
          smiv2:oid "1.3.6.1.4.1.9.9.761.1.1.1.1.10";
        }

        leaf cnsClkSelGlobNofSources {
          type uint32 {
            range "0..255";
          }
          units "clock sources";
          description
           "This object indicates the number of
            synchronization sources currently
            configured for the G.781
            clock selection process.";
          smiv2:max-access "read-only";
          smiv2:oid "1.3.6.1.4.1.9.9.761.1.1.1.1.11";
        }

        leaf cnsClkSelGlobLastHoldoverSeconds {
          type yang:gauge32;
          units "seconds";
          description
           "This object indicates the duration of
            the last holdover period in seconds.
            If the holdover duration is less than a second,
            the object will carry the value zero.";
          smiv2:max-access "read-only";
          smiv2:oid "1.3.6.1.4.1.9.9.761.1.1.1.1.12";
        }

        leaf cnsClkSelGlobCurrHoldoverSeconds {
          type yang:gauge32;
          units "seconds";
          description
           "This object indicates the duration of
            the current holdover period.
            If a system clock is in holdover mode,
            the object carries the current holdover
            duration in seconds. If the system clock
            is not in holdover, the object carries
            the value 0.";
          smiv2:max-access "read-only";
          smiv2:oid "1.3.6.1.4.1.9.9.761.1.1.1.1.13";
        }
      }
    }

    container cnsSelectedInputSourceTable {
      description
       "T0 selected clock source table.
        This table contains the selected clock source for the input T0
        clock.";
      smiv2:oid "1.3.6.1.4.1.9.9.761.1.1.2";

      list cnsSelectedInputSourceEntry {
        key "cnsSelInpSrcNetsyncIndex";
        description
         "An entry is created in the table when the G.781 clock
          selection process has successfully selected a T0 clock
          source.  The entry shall remain during the time
          the G.781 clock selection process remains enabled.";
        smiv2:oid "1.3.6.1.4.1.9.9.761.1.1.2.1";

        leaf cnsSelInpSrcNetsyncIndex {
          type uint32 {
            range "1..4294967295";
          }
          description
           "An index that uniquely represents an entry in
            this table. This index is assigned arbitrarily
            by the clock selection process and may not be persistent
            across reboots.";
          smiv2:max-access "not-accessible";
          smiv2:oid "1.3.6.1.4.1.9.9.761.1.1.2.1.1";
        }

        leaf cnsSelInpSrcName {
          type snmp-framework:SnmpAdminString {
            length "1..255";
          }
          description
           "This object indicates the name of the
            selected T0 clock.";
          smiv2:max-access "read-only";
          smiv2:oid "1.3.6.1.4.1.9.9.761.1.1.2.1.2";
        }

        leaf cnsSelInpSrcIntfType {
          type CISCO-NETSYNC-MIB:CiscoNetsyncIfType;
          description
           "This object indicates the type of the
            selected T0 clock.";
          smiv2:max-access "read-only";
          smiv2:oid "1.3.6.1.4.1.9.9.761.1.1.2.1.3";
        }

        leaf cnsSelInpSrcQualityLevel {
          type CISCO-NETSYNC-MIB:CiscoNetsyncQualityLevel;
          description
           "This object indicates the selected T0 clock
            source's effective quality level, which
            is the derived clock quality based on the three factors: 
            (a) Received quality level. 
            (b) Configured Rx quality level.  This factor supersedes (a). 
            (c) System overridden quality level as a result of exceptional
            events such as signal failure or ESMC failure.  This factor
            supersedes (a) and (b).";
          smiv2:max-access "read-only";
          smiv2:oid "1.3.6.1.4.1.9.9.761.1.1.2.1.4";
        }

        leaf cnsSelInpSrcPriority {
          type uint32 {
            range "1..1024";
          }
          description
           "This object indicates the configured
            priority of the selected T0 clock.
            A smaller value represents a higher priority.";
          reference
           "ITU-T standard G.781 section 5.10";
          smiv2:max-access "read-only";
          smiv2:oid "1.3.6.1.4.1.9.9.761.1.1.2.1.5";
        }

        leaf cnsSelInpSrcTimestamp {
          type yang:timestamp;
          description
           "This object indicates the timestamp of
            the T0 clock source being selected by
            the G.781 clock selection process.";
          smiv2:max-access "read-only";
          smiv2:oid "1.3.6.1.4.1.9.9.761.1.1.2.1.6";
        }

        leaf cnsSelInpSrcFSW {
          type boolean;
          description
           "This object indicates the forced switching flag. Forced
            switching, as described in G.781, is used to override the
            currently selected synchronization source.
            
            The 'true' value indicates the currently selected clock
            source is a result of the forced switching. The 'false'
            value indicates the currently selected clock source is
            not a result of forced switching.";
          reference
           "ITU-T standard G.781 section 5.11.2.2";
          smiv2:max-access "read-only";
          smiv2:oid "1.3.6.1.4.1.9.9.761.1.1.2.1.7";
        }

        leaf cnsSelInpSrcMSW {
          type boolean;
          description
           "This object indicates the manual switching flag.
            The 'true' value indicates the currently selected clock source
            is a result of the manual switch command. The command allows
            a user to select a synchronization source assuming it is
            enabled, not locked out, not in signal fail condition,
            and has a QL better than DNU in QL-enabled mode. Furthermore,
            in QL-enabled mode, a manual switch can be performed only to
            a source which has the highest available QL.";
          reference
           "ITU-T standard G.781 section 5.11.2.3";
          smiv2:max-access "read-only";
          smiv2:oid "1.3.6.1.4.1.9.9.761.1.1.2.1.8";
        }
      }
    }

    container cnsInputSourceTable {
      description
       "T0 clock source table.
        This table contains a list of input sources for input T0 clock
        selection.";
      smiv2:oid "1.3.6.1.4.1.9.9.761.1.1.3";

      list cnsInputSourceEntry {
        key "cnsInpSrcNetsyncIndex";
        description
         "An entry is created in the table when a user adds a T0
          clock source in the configuration. An entry is removed 
          in the table when a user removes a T0 clock source from
          the configuration.";
        smiv2:oid "1.3.6.1.4.1.9.9.761.1.1.3.1";

        leaf cnsInpSrcNetsyncIndex {
          type uint32 {
            range "1..4294967295";
          }
          description
           "An index that uniquely represents an entry in
            this table. This index is assigned arbitrarily
            by the clock selection process and may not be persistent
            across reboots.";
          smiv2:max-access "not-accessible";
          smiv2:oid "1.3.6.1.4.1.9.9.761.1.1.3.1.1";
        }

        leaf cnsInpSrcName {
          type snmp-framework:SnmpAdminString {
            length "1..255";
          }
          description
           "This object indicates the name of an input
            clock source configured for the T0 clock
            selection.";
          smiv2:max-access "read-only";
          smiv2:oid "1.3.6.1.4.1.9.9.761.1.1.3.1.2";
        }

        leaf cnsInpSrcIntfType {
          type CISCO-NETSYNC-MIB:CiscoNetsyncIfType;
          description
           "This object indicates the type of an input
            clock source configured for the T0 clock
            selection.";
          smiv2:max-access "read-only";
          smiv2:oid "1.3.6.1.4.1.9.9.761.1.1.3.1.3";
        }

        leaf cnsInpSrcPriority {
          type uint32 {
            range "1..1024";
          }
          description
           "This object indicates the priority of an input
            clock source configured for the T0 clock
            selection.
            
            A smaller value represents a higher priority.";
          reference
           "ITU-T standard G.781 section 5.10";
          smiv2:max-access "read-only";
          smiv2:oid "1.3.6.1.4.1.9.9.761.1.1.3.1.4";
        }

        leaf cnsInpSrcESMCCap {
          type CISCO-NETSYNC-MIB:CiscoNetsyncESMCCap;
          description
           "This object indicates the ESMC capability
            of an input clock source configured for the
            T0 clock selection.  This is applicable only to Synchronous
            Ethernet input clock source identified by cnsInpSrcIntfType
            'netsyncIfTypeEthernet'.";
          smiv2:max-access "read-only";
          smiv2:oid "1.3.6.1.4.1.9.9.761.1.1.3.1.5";
        }

        leaf cnsInpSrcSSMCap {
          type CISCO-NETSYNC-MIB:CiscoNetsyncSSMCap;
          description
           "This object indicates the SSM capability
            of an input clock source configured for the
            T0 clock selection. This is applicable only to
            any synchronous interface clock source except
            SyncE interface, which is identified by cnsInpSrcIntfType
            'netsyncIfTypeEthernet'.";
          smiv2:max-access "read-only";
          smiv2:oid "1.3.6.1.4.1.9.9.761.1.1.3.1.6";
        }

        leaf cnsInpSrcQualityLevelTxCfg {
          type CISCO-NETSYNC-MIB:CiscoNetsyncQualityLevel;
          description
           "This object indicates the configured transmit
            clock quality level of an input clock source.";
          smiv2:max-access "read-only";
          smiv2:oid "1.3.6.1.4.1.9.9.761.1.1.3.1.7";
        }

        leaf cnsInpSrcQualityLevelRxCfg {
          type CISCO-NETSYNC-MIB:CiscoNetsyncQualityLevel;
          description
           "This object indicates the configured receive
            clock quality level of an input clock source.";
          smiv2:max-access "read-only";
          smiv2:oid "1.3.6.1.4.1.9.9.761.1.1.3.1.8";
        }

        leaf cnsInpSrcQualityLevelTx {
          type CISCO-NETSYNC-MIB:CiscoNetsyncQualityLevel;
          description
           "This object indicates the most recent clock
            quality level transmitted on the input clock
            source.";
          smiv2:max-access "read-only";
          smiv2:oid "1.3.6.1.4.1.9.9.761.1.1.3.1.9";
        }

        leaf cnsInpSrcQualityLevelRx {
          type CISCO-NETSYNC-MIB:CiscoNetsyncQualityLevel;
          description
           "This object indicates the last clock quality
            level received on the input clock source.";
          smiv2:max-access "read-only";
          smiv2:oid "1.3.6.1.4.1.9.9.761.1.1.3.1.10";
        }

        leaf cnsInpSrcQualityLevel {
          type CISCO-NETSYNC-MIB:CiscoNetsyncQualityLevel;
          description
           "This object indicates the current clock quality
            level of the input clock source.  This is the
            effective quality which is derived from three values:
            
            1) most recent clock quality level received,
            2) forced clock quality level (entered via configuration)
            3) overridden clock quality level as a result of line protocol
            down, signal failure, or alarms.";
          smiv2:max-access "read-only";
          smiv2:oid "1.3.6.1.4.1.9.9.761.1.1.3.1.11";
        }

        leaf cnsInpSrcHoldoffTime {
          type uint32 {
            range "0..4294967295";
          }
          units "milliseconds";
          description
           "This object indicates the hold-off time value of
            an input clock source.
            
            The hold-off time prevents short activation of signal failure
            is passed to the selection process.  When a signal failure
            event is reported on a clock source, it waits the duration of
            the hold-off time before declaring signal failure on the clock
            source.";
          reference
           "ITU-T standard G.781 section 5.8";
          smiv2:max-access "read-only";
          smiv2:oid "1.3.6.1.4.1.9.9.761.1.1.3.1.12";
        }

        leaf cnsInpSrcWtrTime {
          type uint32 {
            range "0..4294967295";
          }
          units "Seconds";
          description
           "This object indicates the wait-to-restore time value
            of an input clock source.
            
            The wait-to-restore time ensures that a previous failed
            synchronization source is only again considered as available
            by the selection process if it is fault-free for a certain time.
            When a signal failure condition is cleared on a clock source,
            it waits the duration of the wait-to-restore time before
            clearing the signal failure status on the clock source.";
          reference
           "ITU-T standard G.781 section 5.9";
          smiv2:max-access "read-only";
          smiv2:oid "1.3.6.1.4.1.9.9.761.1.1.3.1.13";
        }

        leaf cnsInpSrcLockout {
          type boolean;
          description
           "This object indicates whether or not the lockout
            command has been applied to a clock source.
            
            The 'true' value means the clock source is not
            considered by the selection process.";
          reference
           "ITU-T standard G.781 section 5.11.1";
          smiv2:max-access "read-only";
          smiv2:oid "1.3.6.1.4.1.9.9.761.1.1.3.1.14";
        }

        leaf cnsInpSrcSignalFailure {
          type boolean;
          description
           "This object indicates whether or not a
            signal failure event is currently being
            reported on the input clock source.";
          reference
           "ITU-T standard G.781 section 5.7";
          smiv2:max-access "read-only";
          smiv2:oid "1.3.6.1.4.1.9.9.761.1.1.3.1.15";
        }

        leaf cnsInpSrcAlarm {
          type boolean;
          description
           "This object indicates whether or not an
            alarm event is currently being reported
            on the input clock source.";
          smiv2:max-access "read-only";
          smiv2:oid "1.3.6.1.4.1.9.9.761.1.1.3.1.16";
        }

        leaf cnsInpSrcAlarmInfo {
          type CISCO-NETSYNC-MIB:CiscoNetsyncAlarmInfo;
          description
           "This object indicates the alarm reasons of
            an input clock source if an alarm event
            is being reported on it.";
          smiv2:max-access "read-only";
          smiv2:oid "1.3.6.1.4.1.9.9.761.1.1.3.1.17";
        }

        leaf cnsInpSrcFSW {
          type boolean;
          description
           "This object indicates the forced switching flag.
            Forced switching, as described in G.781, is used to
            override the currently selected synchronization source.
            
            The 'true' value indicates the currently selected clock source
            is a result of the forced switching. The 'false' value
            indicates the currently selected clock source is not a result
            of forced switching.";
          reference
           "ITU-T standard G.781 section 5.11.2.2";
          smiv2:max-access "read-only";
          smiv2:oid "1.3.6.1.4.1.9.9.761.1.1.3.1.18";
        }

        leaf cnsInpSrcMSW {
          type boolean;
          description
           "This object indicates the manual switching flag.
            
            The 'true' value indicates the currently selected clock source
            is a result of the manual switching. The switch allows
            a user to select a synchronization source assuming it is
            enabled, not locked out, not in signal fail condition,
            and has a QL better than DNU in QL-enabled mode.
            
            A clock source is enabled when it occupies a row in
            cnsInputSourceTable.  A clock source is not locked out
            when cnsInpSrcLockout contains the value 'false'.
            A clock source is not in signal failure condition when
            cnsInpSrcSignalFailure contains the value 'false'. 
            The QL is identified in cnsInpSrcQualityLevel.
            
            In QL-enabled mode, a manual switch can be performed only to
            a source which has the highest available QL.";
          reference
           "ITU-T standard G.781 section 5.11.2.3";
          smiv2:max-access "read-only";
          smiv2:oid "1.3.6.1.4.1.9.9.761.1.1.3.1.19";
        }
      }
    }

    container cnsExtOutputTable {
      description
       "T4 external output table.
        This table contains a list of T4 external outputs.
        
        Each T4 external output is associated with clock
        source(s) to be found in cnsT4ClockSourceTable.
        The clock selection process considers all the
        available clock sources and select the T4 clock
        source based on the G.781 clock selection algorithm.";
      smiv2:oid "1.3.6.1.4.1.9.9.761.1.1.4";

      list cnsExtOutputEntry {
        key "cnsExtOutListIndex";
        description
         "An entry is created in the table when a user adds
          a T4 external output in the configuration.  A T4 external
          output configured input clock sources are defined in
          cnsT4ClockSourceTable.
          
          An entry is removed from the table when a user removes
          a T4 external output from the configuration.";
        smiv2:oid "1.3.6.1.4.1.9.9.761.1.1.4.1";

        leaf cnsExtOutListIndex {
          type uint32 {
            range "1..4294967295";
          }
          description
           "An index that uniquely represents an entry in
            this table.  This index is assigned arbitrarily by the
            clock selection process and may not be persistent
            across reboots.";
          smiv2:max-access "not-accessible";
          smiv2:oid "1.3.6.1.4.1.9.9.761.1.1.4.1.1";
        }

        leaf cnsExtOutSelNetsyncIndex {
          type uint32 {
            range "1..4294967295";
          }
          description
           "An index that uniquely represents the selected input clock
            source whose information is reported by a row in
            cnsT4ClockSourceTable. The index lists the value of
            cnsT4ClkSrcNetsyncIndex, which is the input clock source
            of the T4 external output selected by the G.781 clock
            selection process.";
          smiv2:max-access "read-only";
          smiv2:oid "1.3.6.1.4.1.9.9.761.1.1.4.1.2";
        }

        leaf cnsExtOutName {
          type snmp-framework:SnmpAdminString {
            length "1..255";
          }
          description
           "This object indicates the name of a
            T4 external output.";
          smiv2:max-access "read-only";
          smiv2:oid "1.3.6.1.4.1.9.9.761.1.1.4.1.3";
        }

        leaf cnsExtOutIntfType {
          type CISCO-NETSYNC-MIB:CiscoNetsyncIfType;
          description
           "This object indicates the interface type
            of the T4 external output.";
          smiv2:max-access "read-only";
          smiv2:oid "1.3.6.1.4.1.9.9.761.1.1.4.1.4";
        }

        leaf cnsExtOutQualityLevel {
          type CISCO-NETSYNC-MIB:CiscoNetsyncQualityLevel;
          description
           "This object indicates the clock quality
            of the T4 external output.";
          smiv2:max-access "read-only";
          smiv2:oid "1.3.6.1.4.1.9.9.761.1.1.4.1.5";
        }

        leaf cnsExtOutPriority {
          type uint32 {
            range "1..1024";
          }
          description
           "This object indicates the priority of the
            selected clock source for a T4 external
            output.
            
            A smaller value represents a higher priority.";
          reference
           "ITU-T standard G.781 section 5.10";
          smiv2:max-access "read-only";
          smiv2:oid "1.3.6.1.4.1.9.9.761.1.1.4.1.6";
        }

        leaf cnsExtOutFSW {
          type boolean;
          description
           "This object indicates the forced switching flag.
            Forced switching, as described in G.781, is used to
            override the currently selected synchronization source,
            The T4 selected synchronization source is identified by
            cnsExtOutSelNetsyncIndex, which contains the index to
            the clock source in cnsT4ClockSourceTable.
            
            The 'true' value indicates the currently selected
            T4 clock source is a result of the forced switching.
            The 'false' value indicates the currently selected T4
            clock source is not a result of forced switching.";
          reference
           "ITU-T standard G.781 section 5.11.2.2";
          smiv2:max-access "read-only";
          smiv2:oid "1.3.6.1.4.1.9.9.761.1.1.4.1.7";
        }

        leaf cnsExtOutMSW {
          type boolean;
          description
           "This object indicates the manual switching flag.
            
            The 'true' value indicates the currently selected
            T4 clock source is a result of the manual switch command.
            The command allows a user to select a synchronization source
            assuming it is enabled, not locked out, not in signal fail
            condition, and has a QL better than DNU in QL-enabled mode.
            
            A clock source is enabled when it occupies in row in
            cnsT4ClockSourceTable.  A clock source is not locked out
            when cnsT4ClkSrcLockout contains the value 'false'.
            A clock source is not in signal failure condition when
            cnsT4ClkSrcSignalFailure contains the value 'false'. 
            The QL is identified in cnsT4ClkSrcQualityLevel.
            
            In QL-enabled mode, a manual switch can be 
            performed only to a source which has the highest
            available QL.";
          reference
           "ITU-T standard G.781 section 5.11.2.3";
          smiv2:max-access "read-only";
          smiv2:oid "1.3.6.1.4.1.9.9.761.1.1.4.1.8";
        }

        leaf cnsExtOutSquelch {
          type boolean;
          description
           "This object indicates whether or not a
            T4 external output is squelched.
            
            Squelching is a sychronization function defined to prevent
            transmission of a timing signal with a quality that is lower
            than the quality of the clock in the receiving networks
            element or SASE. It is also used for the prevention of
            timing loops.";
          reference
           "ITU-T standard G.781 section 5.4.1.4";
          smiv2:max-access "read-only";
          smiv2:oid "1.3.6.1.4.1.9.9.761.1.1.4.1.9";
        }
      }
    }

    container cnsT4ClockSourceTable {
      description
       "T4 clock source table.
        This table contains a list of input sources for a specific
        T4 external output. An entry shall be added to
        cnsExtOutputTable first. Then clock sources shall be
        added in this table for the selection process to select
        the appropriate T4 clock source.";
      smiv2:oid "1.3.6.1.4.1.9.9.761.1.1.5";

      list cnsT4ClockSourceEntry {
        key "cnsExtOutListIndex cnsT4ClkSrcNetsyncIndex";
        description
         "An entry is created in the table when a user adds a
          clock source to a T4 external output in the configuration.
          The T4 external output is defined in the T4 external
          output table. An entry is removed in the table when a user
          removes a T4 clock source from the configuration.";
        smiv2:oid "1.3.6.1.4.1.9.9.761.1.1.5.1";

        leaf cnsExtOutListIndex {
          type leafref {
            path "/CISCO-NETSYNC-MIB:CISCO-NETSYNC-MIB/CISCO-NETSYNC-MIB:cnsExtOutputTable/CISCO-NETSYNC-MIB:cnsExtOutputEntry/CISCO-NETSYNC-MIB:cnsExtOutListIndex";
          }
        }

        leaf cnsT4ClkSrcNetsyncIndex {
          type uint32 {
            range "1..4294967295";
          }
          description
           "An index that uniquely represents an entry in
            this table.  This index is assigned arbitrarily by the
            clock selection process and may not be persistent
            across reboots.";
          smiv2:max-access "not-accessible";
          smiv2:oid "1.3.6.1.4.1.9.9.761.1.1.5.1.1";
        }

        leaf cnsT4ClkSrcName {
          type snmp-framework:SnmpAdminString {
            length "1..255";
          }
          description
           "This object indicates the name of a input
            clock source configured for the T4 clock
            selection.";
          smiv2:max-access "read-only";
          smiv2:oid "1.3.6.1.4.1.9.9.761.1.1.5.1.2";
        }

        leaf cnsT4ClkSrcIntfType {
          type CISCO-NETSYNC-MIB:CiscoNetsyncIfType;
          description
           "This object indicates the type of an input
            clock source configured for the T4 clock
            selection.";
          smiv2:max-access "read-only";
          smiv2:oid "1.3.6.1.4.1.9.9.761.1.1.5.1.3";
        }

        leaf cnsT4ClkSrcPriority {
          type uint32 {
            range "1..1024";
          }
          description
           "This object indicates the priority of an input
            clock source configured for the T4 clock
            selection.
            
            A smaller value represents a higher priority.";
          reference
           "ITU-T standard G.781 section 5.10";
          smiv2:max-access "read-only";
          smiv2:oid "1.3.6.1.4.1.9.9.761.1.1.5.1.4";
        }

        leaf cnsT4ClkSrcESMCCap {
          type CISCO-NETSYNC-MIB:CiscoNetsyncESMCCap;
          description
           "This object indicates the ESMC capability
            of an input clock source configured for the
            T4 clock selection.  This is applicable
            only to Synchronous Ethernet input clock source
            identified by cnsT4ClkSrcIntfType 'netsyncIfTypeEthernet'.";
          smiv2:max-access "read-only";
          smiv2:oid "1.3.6.1.4.1.9.9.761.1.1.5.1.5";
        }

        leaf cnsT4ClkSrcSSMCap {
          type CISCO-NETSYNC-MIB:CiscoNetsyncSSMCap;
          description
           "This object indicates the SSM capability
            of an input clock source configured for the
            T4 clock selection. This is applicable only to any
            synchronous interface clock source except SyncE interface,
            which is identified by cnsT4ClkSrcIntfType
            'netsyncIfTypeEthernet'.";
          smiv2:max-access "read-only";
          smiv2:oid "1.3.6.1.4.1.9.9.761.1.1.5.1.6";
        }

        leaf cnsT4ClkSrcQualityLevelTxCfg {
          type CISCO-NETSYNC-MIB:CiscoNetsyncQualityLevel;
          description
           "This object indicates the configured transmit
            clock quality level of a T4 input clock source.";
          smiv2:max-access "read-only";
          smiv2:oid "1.3.6.1.4.1.9.9.761.1.1.5.1.7";
        }

        leaf cnsT4ClkSrcQualityLevelRxCfg {
          type CISCO-NETSYNC-MIB:CiscoNetsyncQualityLevel;
          description
           "This object indicates the configured receive
            clock quality level of a T4 input clock source.";
          smiv2:max-access "read-only";
          smiv2:oid "1.3.6.1.4.1.9.9.761.1.1.5.1.8";
        }

        leaf cnsT4ClkSrcQualityLevelTx {
          type CISCO-NETSYNC-MIB:CiscoNetsyncQualityLevel;
          description
           "This object indicates the most recent clock
            quality level transmitted on the T4 input
            clock source.";
          smiv2:max-access "read-only";
          smiv2:oid "1.3.6.1.4.1.9.9.761.1.1.5.1.9";
        }

        leaf cnsT4ClkSrcQualityLevelRx {
          type CISCO-NETSYNC-MIB:CiscoNetsyncQualityLevel;
          description
           "This object indicates the last clock quality
            level received on the T4 input clock
            source.";
          smiv2:max-access "read-only";
          smiv2:oid "1.3.6.1.4.1.9.9.761.1.1.5.1.10";
        }

        leaf cnsT4ClkSrcQualityLevel {
          type CISCO-NETSYNC-MIB:CiscoNetsyncQualityLevel;
          description
           "This object indicates the current clock quality
            level of the T4 input clock source.  This is the
            effective quality which is derived from three values:
            
            1) most recent clock quality level received,
            2) forced clock quality level (entered via configuration)
            3) overridden clock quality level as a result of line protocol
            down, signal failure, or alarms.";
          smiv2:max-access "read-only";
          smiv2:oid "1.3.6.1.4.1.9.9.761.1.1.5.1.11";
        }

        leaf cnsT4ClkSrcHoldoffTime {
          type uint32 {
            range "0..4294967295";
          }
          units "milliseconds";
          description
           "This object indicates the hold-off time value of
            a T4 input clock source.
            
            The hold-off time prevents short activation of signal failure
            is passed to the selection process.  When a signal failure
            event is reported on a clock source, it waits the duration of
            the hold-off time before declaring signal failure on the clock
            source.";
          reference
           "ITU-T standard G.781 section 5.8";
          smiv2:max-access "read-only";
          smiv2:oid "1.3.6.1.4.1.9.9.761.1.1.5.1.12";
        }

        leaf cnsT4ClkSrcWtrTime {
          type uint32 {
            range "0..4294967295";
          }
          units "seconds";
          description
           "This object indicates the wait-to-restore time value
            of a T4 input clock source.
            
            The wait-to-restore time ensures that a previous failed
            synchronization source is only again considered as available
            by the selection process if it is fault-free for a certain time.
            When a signal failure condition is cleared on a clock source,
            it waits the duration of the wait-to-restore time before
            clearing the signal failure status on the clock source.";
          reference
           "ITU-T standard G.781 section 5.9";
          smiv2:max-access "read-only";
          smiv2:oid "1.3.6.1.4.1.9.9.761.1.1.5.1.13";
        }

        leaf cnsT4ClkSrcLockout {
          type boolean;
          description
           "This object indicates whether or not the lockout
            command has been applied on a T4 clock source.
            
            The 'true' value means the clock source is not
            considered by the selection process.";
          reference
           "ITU-T standard G.781 section 5.11.1";
          smiv2:max-access "read-only";
          smiv2:oid "1.3.6.1.4.1.9.9.761.1.1.5.1.14";
        }

        leaf cnsT4ClkSrcSignalFailure {
          type boolean;
          description
           "This object indicates whether or not a
            signal failure event is currently being
            reported on the T4 input clock source.";
          reference
           "ITU-T standard G.781 section 5.7";
          smiv2:max-access "read-only";
          smiv2:oid "1.3.6.1.4.1.9.9.761.1.1.5.1.15";
        }

        leaf cnsT4ClkSrcAlarm {
          type boolean;
          description
           "This object indicates whether or not an
            alarm event is currently being reported
            on the T4 input clock source.";
          smiv2:max-access "read-only";
          smiv2:oid "1.3.6.1.4.1.9.9.761.1.1.5.1.16";
        }

        leaf cnsT4ClkSrcAlarmInfo {
          type CISCO-NETSYNC-MIB:CiscoNetsyncAlarmInfo;
          description
           "This object indicates the alarm reasons of
            a T4 input clock source if an alarm event
            is being reported on the clock source.";
          smiv2:max-access "read-only";
          smiv2:oid "1.3.6.1.4.1.9.9.761.1.1.5.1.17";
        }

        leaf cnsT4ClkSrcFSW {
          type boolean;
          description
           "This object indicates the forced switching flag.
            Forced switching, as described in G.781, is used to
            override the currently selected synchronization source.
            
            The 'true' value indicates the currently selected
            T4 clock source is a result of the forced switching.
            The 'false' value indicates the currently selected
            T4 clock source is not a result of forced switching.";
          reference
           "ITU-T standard G.781 section 5.11.2.2";
          smiv2:max-access "read-only";
          smiv2:oid "1.3.6.1.4.1.9.9.761.1.1.5.1.18";
        }

        leaf cnsT4ClkSrcMSW {
          type boolean;
          description
           "This object indicates the manual switching flag.
            
            The 'true' value indicates the currently selected
            T4 clock source is a result of the manual switching.
            The switch allows a user to select a 
            synchronization source assuming it is enabled,
            not locked out, not in signal fail condition,
            and has a QL better than DNU in QL-enabled mode.
            
            A clock source is enabled when it occupies a row in 
            cnsT4ClockSourceTable.  A clock source is not locked
            out when cnsT4ClkSrcLockout contains the value 'false'.
            A clock source is not in signal failure condition when
            cnsT4ClkSrcSignalFailure contains the value 'false'.
            The QL is identified in cnsT4ClkSrcQualityLevel.
            
            In QL-enabled mode, a manual switch
            can be performed only to a source which has the
            highest available QL.";
          reference
           "ITU-T standard G.781 section 5.11.2.3";
          smiv2:max-access "read-only";
          smiv2:oid "1.3.6.1.4.1.9.9.761.1.1.5.1.19";
        }
      }
    }
  }

  notification ciscoNetsyncSelectedT0Clock {
    description
     "T0 clock selection notification.
      
      This notification is generated when one
      of the following conditions is met:
      
      - A new clock source is selected by the
        T0 clock selection.
      - The clock quality of a T0 selected clock 
        source is changed.
      - The configured priority of a T0 selected
        clock source is changed.";
    smiv2:oid "1.3.6.1.4.1.9.9.761.0.1";

    container object-1 {

      leaf cnsSelInpSrcNetsyncIndex {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcNetsyncIndex";
        }
      }

      leaf cnsSelInpSrcName {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcName";
        }
      }
    }

    container object-2 {

      leaf cnsSelInpSrcNetsyncIndex {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcNetsyncIndex";
        }
      }

      leaf cnsSelInpSrcIntfType {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcIntfType";
        }
      }
    }

    container object-3 {

      leaf cnsSelInpSrcNetsyncIndex {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcNetsyncIndex";
        }
      }

      leaf cnsSelInpSrcQualityLevel {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcQualityLevel";
        }
      }
    }

    container object-4 {

      leaf cnsSelInpSrcNetsyncIndex {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcNetsyncIndex";
        }
      }

      leaf cnsSelInpSrcPriority {
        type leafref {
          path "/CISCO-NETSYNC-MIB:CISCO-NETSYNC-MIB/CISCO-NETSYNC-MIB:cnsSelectedInputSourceTable/CISCO-NETSYNC-MIB:cnsSelectedInputSourceEntry/CISCO-NETSYNC-MIB:cnsSelInpSrcPriority";
        }
      }
    }
  }

  notification ciscoNetsyncSelectedT4Clock {
    description
     "T4 clock selection notification.
      
      This notification is generated when one
      of the following conditions is met:
      
      - A new clock source is selected by the
        T4 clock selection.
      - The clock quality of a T4 selected clock 
        source is changed.
      - The configured priority of a T4 selected
        clock source is changed.";
    smiv2:oid "1.3.6.1.4.1.9.9.761.0.2";

    container object-1 {

      leaf cnsExtOutListIndex {
        type leafref {
          path "/CISCO-NETSYNC-MIB:CISCO-NETSYNC-MIB/CISCO-NETSYNC-MIB:cnsExtOutputTable/CISCO-NETSYNC-MIB:cnsExtOutputEntry/CISCO-NETSYNC-MIB:cnsExtOutListIndex";
        }
      }

      leaf cnsExtOutName {
        type leafref {
          path "/CISCO-NETSYNC-MIB:CISCO-NETSYNC-MIB/CISCO-NETSYNC-MIB:cnsExtOutputTable/CISCO-NETSYNC-MIB:cnsExtOutputEntry/CISCO-NETSYNC-MIB:cnsExtOutName";
        }
      }
    }

    container object-2 {

      leaf cnsExtOutListIndex {
        type leafref {
          path "/CISCO-NETSYNC-MIB:CISCO-NETSYNC-MIB/CISCO-NETSYNC-MIB:cnsExtOutputTable/CISCO-NETSYNC-MIB:cnsExtOutputEntry/CISCO-NETSYNC-MIB:cnsExtOutListIndex";
        }
      }

      leaf cnsT4ClkSrcNetsyncIndex {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcNetsyncIndex";
        }
      }

      leaf cnsT4ClkSrcName {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcName";
        }
      }
    }

    container object-3 {

      leaf cnsExtOutListIndex {
        type leafref {
          path "/CISCO-NETSYNC-MIB:CISCO-NETSYNC-MIB/CISCO-NETSYNC-MIB:cnsExtOutputTable/CISCO-NETSYNC-MIB:cnsExtOutputEntry/CISCO-NETSYNC-MIB:cnsExtOutListIndex";
        }
      }

      leaf cnsT4ClkSrcNetsyncIndex {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcNetsyncIndex";
        }
      }

      leaf cnsT4ClkSrcIntfType {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcIntfType";
        }
      }
    }

    container object-4 {

      leaf cnsExtOutListIndex {
        type leafref {
          path "/CISCO-NETSYNC-MIB:CISCO-NETSYNC-MIB/CISCO-NETSYNC-MIB:cnsExtOutputTable/CISCO-NETSYNC-MIB:cnsExtOutputEntry/CISCO-NETSYNC-MIB:cnsExtOutListIndex";
        }
      }

      leaf cnsT4ClkSrcNetsyncIndex {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcNetsyncIndex";
        }
      }

      leaf cnsT4ClkSrcQualityLevel {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcQualityLevel";
        }
      }
    }

    container object-5 {

      leaf cnsExtOutListIndex {
        type leafref {
          path "/CISCO-NETSYNC-MIB:CISCO-NETSYNC-MIB/CISCO-NETSYNC-MIB:cnsExtOutputTable/CISCO-NETSYNC-MIB:cnsExtOutputEntry/CISCO-NETSYNC-MIB:cnsExtOutListIndex";
        }
      }

      leaf cnsT4ClkSrcNetsyncIndex {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcNetsyncIndex";
        }
      }

      leaf cnsT4ClkSrcPriority {
        type leafref {
          path "/CISCO-NETSYNC-MIB:CISCO-NETSYNC-MIB/CISCO-NETSYNC-MIB:cnsT4ClockSourceTable/CISCO-NETSYNC-MIB:cnsT4ClockSourceEntry/CISCO-NETSYNC-MIB:cnsT4ClkSrcPriority";
        }
      }
    }
  }

  notification ciscoNetsyncInputSignalFailureStatus {
    description
     "Input clock source signal failure notification.
      
      This notification is generated when a signal
      failure event is reported on an input clock source.
      One of the conditions a signal failure event
      could be due to interface shutdown.";
    smiv2:oid "1.3.6.1.4.1.9.9.761.0.3";

    container object-1 {

      leaf cnsInpSrcNetsyncIndex {
        type leafref {
          path "/CISCO-NETSYNC-MIB:CISCO-NETSYNC-MIB/CISCO-NETSYNC-MIB:cnsInputSourceTable/CISCO-NETSYNC-MIB:cnsInputSourceEntry/CISCO-NETSYNC-MIB:cnsInpSrcNetsyncIndex";
        }
      }

      leaf cnsInpSrcName {
        type leafref {
          path "/CISCO-NETSYNC-MIB:CISCO-NETSYNC-MIB/CISCO-NETSYNC-MIB:cnsInputSourceTable/CISCO-NETSYNC-MIB:cnsInputSourceEntry/CISCO-NETSYNC-MIB:cnsInpSrcName";
        }
      }
    }

    container object-2 {

      leaf cnsInpSrcNetsyncIndex {
        type leafref {
          path "/CISCO-NETSYNC-MIB:CISCO-NETSYNC-MIB/CISCO-NETSYNC-MIB:cnsInputSourceTable/CISCO-NETSYNC-MIB:cnsInputSourceEntry/CISCO-NETSYNC-MIB:cnsInpSrcNetsyncIndex";
        }
      }

      leaf cnsInpSrcIntfType {
        type leafref {
          path "/CISCO-NETSYNC-MIB:CISCO-NETSYNC-MIB/CISCO-NETSYNC-MIB:cnsInputSourceTable/CISCO-NETSYNC-MIB:cnsInputSourceEntry/CISCO-NETSYNC-MIB:cnsInpSrcIntfType";
        }
      }
    }

    container object-3 {

      leaf cnsInpSrcFailClear {
        type boolean;
        description
         "This object indicates the clear status of a signal failure
          event. A value of 'true' means a signal failure event reported
          on a clock source has been cleared.  A value of 'false' means
          a signal event has been reported on a clock source.";
        smiv2:max-access "accessible-for-notify";
        smiv2:oid "1.3.6.1.4.1.9.9.761.1.2.1";
      }
    }
  }

  notification ciscoNetsyncInputAlarmStatus {
    description
     "Input clock source alarm notification.
      
      This notification is generated when an alarm
      event is reported on an input clock source.";
    smiv2:oid "1.3.6.1.4.1.9.9.761.0.4";

    container object-1 {

      leaf cnsInpSrcNetsyncIndex {
        type leafref {
          path "/CISCO-NETSYNC-MIB:CISCO-NETSYNC-MIB/CISCO-NETSYNC-MIB:cnsInputSourceTable/CISCO-NETSYNC-MIB:cnsInputSourceEntry/CISCO-NETSYNC-MIB:cnsInpSrcNetsyncIndex";
        }
      }

      leaf cnsInpSrcName {
        type leafref {
          path "/CISCO-NETSYNC-MIB:CISCO-NETSYNC-MIB/CISCO-NETSYNC-MIB:cnsInputSourceTable/CISCO-NETSYNC-MIB:cnsInputSourceEntry/CISCO-NETSYNC-MIB:cnsInpSrcName";
        }
      }
    }

    container object-2 {

      leaf cnsInpSrcNetsyncIndex {
        type leafref {
          path "/CISCO-NETSYNC-MIB:CISCO-NETSYNC-MIB/CISCO-NETSYNC-MIB:cnsInputSourceTable/CISCO-NETSYNC-MIB:cnsInputSourceEntry/CISCO-NETSYNC-MIB:cnsInpSrcNetsyncIndex";
        }
      }

      leaf cnsInpSrcIntfType {
        type leafref {
          path "/CISCO-NETSYNC-MIB:CISCO-NETSYNC-MIB/CISCO-NETSYNC-MIB:cnsInputSourceTable/CISCO-NETSYNC-MIB:cnsInputSourceEntry/CISCO-NETSYNC-MIB:cnsInpSrcIntfType";
        }
      }
    }

    container object-3 {

      leaf cnsInpSrcNetsyncIndex {
        type leafref {
          path "/CISCO-NETSYNC-MIB:CISCO-NETSYNC-MIB/CISCO-NETSYNC-MIB:cnsInputSourceTable/CISCO-NETSYNC-MIB:cnsInputSourceEntry/CISCO-NETSYNC-MIB:cnsInpSrcNetsyncIndex";
        }
      }

      leaf cnsInpSrcAlarmInfo {
        type leafref {
          path "/CISCO-NETSYNC-MIB:CISCO-NETSYNC-MIB/CISCO-NETSYNC-MIB:cnsInputSourceTable/CISCO-NETSYNC-MIB:cnsInputSourceEntry/CISCO-NETSYNC-MIB:cnsInpSrcAlarmInfo";
        }
      }
    }

    container object-4 {

      leaf cnsInpSrcAlarmClear {
        type boolean;
        description
         "This object indicates the clear status of an alarm event.
          A value of 'true' means an alarm event reported on a clock
          source has been cleared.  A value of 'false' means an alarm
          event has been reported on a clock source.";
        smiv2:max-access "accessible-for-notify";
        smiv2:oid "1.3.6.1.4.1.9.9.761.1.2.2";
      }
    }
  }

  smiv2:alias "ciscoNetsyncMIB" {
    smiv2:oid "1.3.6.1.4.1.9.9.761";
  }

  smiv2:alias "ciscoNetsyncMIBNotifs" {
    smiv2:oid "1.3.6.1.4.1.9.9.761.0";
  }

  smiv2:alias "ciscoNetsyncMIBObjects" {
    smiv2:oid "1.3.6.1.4.1.9.9.761.1";
  }

  smiv2:alias "ciscoNetsyncMIBTables" {
    smiv2:oid "1.3.6.1.4.1.9.9.761.1.1";
  }

  smiv2:alias "cnsNotifObjects" {
    smiv2:oid "1.3.6.1.4.1.9.9.761.1.2";
  }

  smiv2:alias "ciscoNetsyncMIBNotifControl" {
    smiv2:oid "1.3.6.1.4.1.9.9.761.1.3";
  }

  smiv2:alias "ciscoNetsyncMIBConform" {
    smiv2:oid "1.3.6.1.4.1.9.9.761.2";
  }

  smiv2:alias "ciscoNetsyncMIBCompliances" {
    smiv2:oid "1.3.6.1.4.1.9.9.761.2.1";
  }

  smiv2:alias "ciscoNetsyncMIBGroups" {
    smiv2:oid "1.3.6.1.4.1.9.9.761.2.2";
  }

}
