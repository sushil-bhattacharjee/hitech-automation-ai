/*
 * Generated by confdc --mib2yang-std
 * Source: mgmt/dmi/model/mib/src/CISCO-IETF-PW-TC-MIB.mib
 */
/*
 * This YANG module has been generated by smidump 0.5.0:
 *
 *      smidump -f yang CISCO-IETF-PW-TC-MIB
 *
 * Do not edit. Edit the source file instead!
 */

module CISCO-IETF-PW-TC-MIB {

  namespace "urn:ietf:params:xml:ns:yang:smiv2:CISCO-IETF-PW-TC-MIB";
  prefix CISCO-IETF-PW-TC-MIB;

  import ietf-yang-smiv2 {
    prefix "smiv2";
  }

  organization
   "Cisco Systems, Inc.";

  contact
   " 
    Thomas D. Nadeau 
    Postal: Cisco Systems, Inc. 
            250 Apollo Drive 
            Chelmsford, MA 01824 
    Tel:    +1-978-497-3051 
    Email:  tnadeau@cisco.com 
    
    MPLS MIB Development Team
    Postal: Cisco Systems, Inc.
            250 Apollo Drive
            Chelmsford, MA 01924
    Tel:    +1-978-497-3989
    Email:  ch-mpls-mib-dev@cisco.com";

  description
   "This MIB Module provides Textual Conventions 
    and OBJECT-IDENTITY Objects to be used PW services.";

  revision 2006-07-21 {
    description
     "Added following enumerations to cpwVcType TC:
      e1Satop(12), t1Satop(13), e3Satop(14), t3Satop(15), 
      basicCesPsn(16), basicTdmIp(17), tdmCasCesPsn(18),
      tdmCasTdmIp(19). The above enumerations are based 
      on IANAPwTypeTC TC in draft-ietf-pwe3-pw-mib-08.txt";
  }

  revision 2003-02-26 {
    description
     "Made Cisco proprietary based on the PW-TC-MIB.my file
      extracted from draft-ietf-pwe3-pw-tc-mib-00.txt";
  }

  revision 2002-05-28 {
    description
     "Adding PwVcType, and enhance some descriptions.";
  }

  revision 2002-01-30 {
    description
     "Adding PwVcVlanCfg, PwAddressType and  
      PwOperStatus.";
  }

  revision 2001-12-20 {
    description
     "Remove PwVcInstance";
  }

  revision 2001-07-12 {
    description
     "Initial version.";
  }

  typedef CpwGroupID {
    type uint32;
    description
     "An administrative identification mechanism for grouping a 
      set of service-specific pseudo-wire services. May only 
      have local significance.";
  }

  typedef CpwVcIDType {
    type uint32;
    description
     "Virtual Circuit Identifier. Used to identify the VC  
      (together with some other fields) in the signaling  
      session. Zero if the VC is set-up manually.";
  }

  typedef CpwVcIndexType {
    type uint32;
    description
     "Virtual Circuit Index. Locally unique index for indexing 
      several MIB tables associated with a particular VC.";
  }

  typedef CpwVcVlanCfg {
    type int32 {
      range "0..4097";
    }
    description
     "VLAN configuration for Ethernet PW.  
      Values between 0 to 4095 indicate the actual VLAN field 
      value.  
      A value of 4096 indicates that the object refer to  
      untagged frames, i.e. frames without 802.1Q field. 
      A value of 4097 indicates that the object is not  
      relevant.";
  }

  typedef CpwOperStatus {
    type enumeration {
      enum "up" {
        value "1";
      }
      enum "down" {
        value "2";
      }
      enum "testing" {
        value "3";
      }
      enum "unknown" {
        value "4";
      }
      enum "dormant" {
        value "5";
      }
      enum "notPresent" {
        value "6";
      }
      enum "lowerLayerDown" {
        value "7";
      }
    }
    description
     "Indicate the operational status of the PW VC. 
      
      - up:             Ready to pass packets.  
      - down:           If PW signaling has not yet finished, or 
                        indications available at the service  
                        level indicate that the VC is not  
                        passing packets. 
      - testing:        If AdminStatus at the VC level is set to  
                        test. 
      - dormant:        The VC is not available because of the 
                        required resources are occupied VC with  
                        higher priority VCs . 
      - notPresent:     Some component is missing to accomplish  
                        the set up of the VC. 
      - lowerLayerDown: The underlying PSN or outer tunnel is not 
                        in OperStatus 'up'.  ";
  }

  typedef CpwVcType {
    type enumeration {
      enum "other" {
        value "0";
      }
      enum "frameRelay" {
        value "1";
      }
      enum "atmAal5Vcc" {
        value "2";
      }
      enum "atmTransparent" {
        value "3";
      }
      enum "ethernetVLAN" {
        value "4";
      }
      enum "ethernet" {
        value "5";
      }
      enum "hdlc" {
        value "6";
      }
      enum "ppp" {
        value "7";
      }
      enum "cep" {
        value "8";
      }
      enum "atmVccCell" {
        value "9";
      }
      enum "atmVpcCell" {
        value "10";
      }
      enum "ethernetVPLS" {
        value "11";
      }
      enum "e1Satop" {
        value "12";
      }
      enum "t1Satop" {
        value "13";
      }
      enum "e3Satop" {
        value "14";
      }
      enum "t3Satop" {
        value "15";
      }
      enum "basicCesPsn" {
        value "16";
      }
      enum "basicTdmIp" {
        value "17";
      }
      enum "tdmCasCesPsn" {
        value "18";
      }
      enum "tdmCasTdmIp" {
        value "19";
      }
    }
    description
     "Indicate the VC type (i.e. the carried service). 
      Note: the exact set of VC types is yet to be worked  
      out by the WG. ";
  }

  smiv2:alias "cpwMIB" {
    smiv2:oid "1.3.6.1.4.1.9.10.20000";
  }

  smiv2:alias "cpwTCMIB" {
    smiv2:oid "1.3.6.1.4.1.9.10.20000.1";
  }

}
