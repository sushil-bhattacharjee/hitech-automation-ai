submodule openconfig-mpls-igp {

  yang-version "1";

  belongs-to "openconfig-mpls" {
    prefix "oc-mpls";
  }


  // import some basic types
  import openconfig-mpls-ldp { prefix oc-ldp; }
  import openconfig-extensions { prefix oc-ext; }



  // meta
  organization "OpenConfig working group";

  contact
    "OpenConfig working group
    netopenconfig@googlegroups.com";

  description
    "Configuration generic configuration parameters for IGP-congruent
    LSPs";

  oc-ext:openconfig-version "2.1.0";

  revision "2016-12-15" {
    description
      "Add additional MPLS parameters";
    reference "2.1.0";
  }

  revision "2016-09-01" {
    description
      "Revisions based on implementation feedback";
    reference "2.0.0";
  }

  revision "2016-08-08" {
    description
      "Public release of MPLS models";
    reference "1.0.1";
  }

  // grouping statements


  grouping igp-lsp-common {
    description
      "common definitions for IGP-congruent LSPs";

  }


  grouping igp-lsp-setup {
    description
      "signaling protocol definitions for IGP-based LSPs";

    container path-setup-protocol {
      description
        "select and configure the signaling method for
          the LSP";

      // uses path-setup-common;
      uses oc-ldp:igp-lsp-ldp-setup;
    }
  }


  // data definition statements

  // augment statements

  // rpc statements

  // notification statements

}
