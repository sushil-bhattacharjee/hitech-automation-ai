module Cisco-IOS-XE-crypto-actions-rpc {
  yang-version 1;
  namespace "http://cisco.com/ns/yang/Cisco-IOS-XE-crypto-actions-rpc";
  prefix crypto-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Crypto RPC.
     Copyright (c) 2020 by Cisco Systems, Inc.
     All rights reserved.";

  revision 2021-03-01 {
    description
      "Initial revision";
    reference
      "1.0.0";
    cisco-semver:module-version "1.0.0";
  }

  typedef crypto-clear-enum {
    type enumeration {
      enum crypto-clear-pki-counters {
        value 0;
        description
          "Clear PKI counters";
      }
    }
    description
      "Clear crypto type";
  }

  grouping crypto-clear-type {
    description
      "Top level global crypto clear command";
    leaf clear-type {
      type crypto-actions-rpc:crypto-clear-enum;
      mandatory true;
      description
        "crypto clear sub command";
    }
  }

  rpc crypto-clear {
    description
      "Crypto action RPC";
    input {
      uses crypto-actions-rpc:crypto-clear-type;
    }
  }
}
