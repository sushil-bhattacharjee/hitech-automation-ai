module Cisco-IOS-XE-flow-rpc {
  namespace "http://cisco.com/ns/yang/Cisco-IOS-XE-flow-rpc";
  prefix ios-xe-flow-rpc;

  import cisco-semver {
    prefix cisco-semver;
  }
  import Cisco-IOS-XE-rpc {
    prefix ios-xe-rpc;
  }

  organization
    "Cisco Systems";
  contact
    "<mailto:cs-yang@cisco.com>";
  description
    "NED Flow RPC YANG module for IOS
     Copyright (c) 2016-2019 by Cisco Systems, Inc.
     All rights reserved.";

  revision 2019-07-01 {
    description
      "Establish semantic version baseline";
    cisco-semver:module-version "1.0.0";
  }
  revision 2018-12-06 {
    description
      "created for NED RPC modularisation";
  }

  augment "/ios-xe-rpc:clear/ios-xe-rpc:input/ios-xe-rpc:clear-choice" {
    case flow-case {
      container flow {
        description
          "Flow monitor clear commands";
        choice flow-choice {
          case monitor-case {
            container monitor {
              leaf name {
                mandatory true;
                type string;
              }
              choice monitor-option {
                leaf force-export {
                  type empty;
                }
                leaf statistics {
                  type empty;
                }
                container cache {
                  leaf force-export {
                    type empty;
                  }
                }
              }
            }
          }
          case export-case {
            container exporter {
              leaf name {
                type string;
              }
              leaf statistics {
                type empty;
              }
            }
          }
        }
      }
    }
  }
}
