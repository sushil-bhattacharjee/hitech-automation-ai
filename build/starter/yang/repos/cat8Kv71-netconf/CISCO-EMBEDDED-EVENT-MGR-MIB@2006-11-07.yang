/*
 * Generated by confdc --mib2yang-std
 * Source: mgmt/dmi/model/mib/src/CISCO-EMBEDDED-EVENT-MGR-MIB.mib
 */
/*
 * This YANG module has been generated by smidump 0.5.0:
 *
 *      smidump -f yang CISCO-EMBEDDED-EVENT-MGR-MIB
 *
 * Do not edit. Edit the source file instead!
 */

module CISCO-EMBEDDED-EVENT-MGR-MIB {

  namespace "urn:ietf:params:xml:ns:yang:smiv2:CISCO-EMBEDDED-EVENT-MGR-MIB";
  prefix CISCO-EMBEDDED-EVENT-MGR-MIB;

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 West Tasman Drive
    San Jose, CA 95134 USA
    
    Tel: +1 800 553-NETS
    
    E-mail:  cs-embedded-event-manager@cisco.com";

  description
   "The MIB module to describe and store events generated
    by the Cisco Embedded Event Manager.  
    
    The Cisco Embedded Event Manager detects hardware and software 
    faults, and other events (such as OIRs) for the system.
    It also enables users to configure fault recovery services
    for system wide components.  The Embedded Event Manager also 
    provides process reliability statistics.
    
    The Embedded Event Manager is a policy driven process through 
    which faults in the system are reported through a defined API.
    The Embedded Event Manager policy engine receives notifications
    when faults and other events occur.  Embedded Event Manager 
    policies implement recovery based on the current state of the 
    system and the actions specified in the policy for a given 
    event.  Recovery actions are triggered when the policy is 
    run.  Developers write and customize Embedded Event Manager 
    policies to handle faults and events.";

  revision 2006-11-07 {
    description
     "Added eventType5 to eventType8.";
  }

  revision 2003-04-16 {
    description
     "Initial version of this MIB.";
  }

  typedef NotifySource {
    type enumeration {
      enum "server" {
        value "1";
      }
      enum "policy" {
        value "2";
      }
    }
    description
     "The notification source of the history entry.
      server - Notification was sent by the Embedded Event 
               Manager server.
      policy - Notification was sent from within an Embedded 
               Event Manager policy.";
  }


  container CISCO-EMBEDDED-EVENT-MGR-MIB {
    config false;

    container ceemHistory {
      smiv2:oid "1.3.6.1.4.1.9.10.134.1.2";

      leaf ceemHistoryMaxEventEntries {
        type int32 {
          range "0..50";
        }
        description
         "The maximum number of entries that can be held in
          ceemHistoryEventTable.";
        smiv2:defval "10";
        smiv2:max-access "read-write";
        smiv2:oid "1.3.6.1.4.1.9.10.134.1.2.1";
      }

      leaf ceemHistoryLastEventEntry {
        type uint32 {
          range "1..4294967295";
        }
        description
         "Index of last entry created in ceemHistoryEventTable.";
        smiv2:max-access "read-only";
        smiv2:oid "1.3.6.1.4.1.9.10.134.1.2.2";
      }
    }

    container ceemEventMapTable {
      description
       "A table containing information about ceemEventIndex
        value mapping.  Each conceptual row specifies a 
        unique mapping between a ceemEventIndex value, and a 
        Embedded Event Manager event type.  Rows are added 
        dynamically as the Embedded Event Manager server learns
        of new event types.  This occurs when Embedded Event 
        Manager Event Detectors register with the Embedded 
        Event Manager server.";
      smiv2:oid "1.3.6.1.4.1.9.10.134.1.1.1";

      list ceemEventMapEntry {
        key "ceemEventIndex";
        description
         "A mapping between an event type and an event description.";
        smiv2:oid "1.3.6.1.4.1.9.10.134.1.1.1.1";

        leaf ceemEventIndex {
          type uint32;
          description
           "This object uniquely identifies an event.  Events
            are not persisted across reloads.";
          smiv2:max-access "not-accessible";
          smiv2:oid "1.3.6.1.4.1.9.10.134.1.1.1.1.1";
        }

        leaf ceemEventName {
          type snmp-framework:SnmpAdminString {
            length "1..128";
          }
          description
           "The name of the Embedded Event Manager event.";
          smiv2:max-access "read-only";
          smiv2:oid "1.3.6.1.4.1.9.10.134.1.1.1.1.2";
        }

        leaf ceemEventDescrText {
          type snmp-framework:SnmpAdminString;
          description
           "This object specifies a human-readable
            message describing information about the 
            Embedded Event Manager event.";
          smiv2:max-access "read-only";
          smiv2:oid "1.3.6.1.4.1.9.10.134.1.1.1.1.3";
        }
      }
    }

    container ceemHistoryEventTable {
      description
       "A table of Embedded Event Manager events generated by this
        router.  Conceptual row entries are dynamically added into 
        this table when Embedded Event Manager events occur.
        
        Entries are stored in FIFO order.  When the maximum number 
        of entries has been reached in the table, the oldest entry 
        in the table is removed immediately.  
        
        When a table is reduced to a smaller size N, the oldest
        entries are immediately removed from the table leaving 
        a maximum of N entries.";
      smiv2:oid "1.3.6.1.4.1.9.10.134.1.2.3";

      list ceemHistoryEventEntry {
        key "ceemHistoryEventIndex";
        description
         "Information about an Embedded Event Manager event which has
          been generated by this router.  It provides up to four event
          types to support complex event specifications that are
          triggered when multiple events are published within a certain
          period of time.";
        smiv2:oid "1.3.6.1.4.1.9.10.134.1.2.3.1";

        leaf ceemHistoryEventIndex {
          type uint32 {
            range "1..4294967295";
          }
          description
           "A monotonically increasing non-zero integer uniquely
            identifying a generated event.  When it reaches the 
            maximum value, the agent wraps the value back to 1 
            and may flush all existing entries in the event table.";
          smiv2:max-access "not-accessible";
          smiv2:oid "1.3.6.1.4.1.9.10.134.1.2.3.1.1";
        }

        leaf ceemHistoryEventType1 {
          type uint32;
          description
           "The type of Embedded Event Manager event which was
            detected. The value corresponds to an entry in the 
            ceemEventTable.";
          smiv2:max-access "read-only";
          smiv2:oid "1.3.6.1.4.1.9.10.134.1.2.3.1.2";
        }

        leaf ceemHistoryEventType2 {
          type uint32;
          description
           "The type of Embedded Event Manager event which was
            detected. The value corresponds to an entry in the 
            ceemEventTable.";
          smiv2:max-access "read-only";
          smiv2:oid "1.3.6.1.4.1.9.10.134.1.2.3.1.3";
        }

        leaf ceemHistoryEventType3 {
          type uint32;
          description
           "The type of Embedded Event Manager event which was
            detected. The value corresponds to an entry in the 
            ceemEventTable.";
          smiv2:max-access "read-only";
          smiv2:oid "1.3.6.1.4.1.9.10.134.1.2.3.1.4";
        }

        leaf ceemHistoryEventType4 {
          type uint32;
          description
           "The type of Embedded Event Manager event which was
            detected. The value corresponds to an entry in the
            ceemEventTable.";
          smiv2:max-access "read-only";
          smiv2:oid "1.3.6.1.4.1.9.10.134.1.2.3.1.5";
        }

        leaf ceemHistoryPolicyPath {
          type snmp-framework:SnmpAdminString {
            length "0..128";
          }
          description
           "The file path on the router where the Embedded Event Manager
            policy that was triggered is stored.  If the size of the 
            file path string is larger than 128, the end characters 
            will be truncated.";
          smiv2:max-access "read-only";
          smiv2:oid "1.3.6.1.4.1.9.10.134.1.2.3.1.6";
        }

        leaf ceemHistoryPolicyName {
          type snmp-framework:SnmpAdminString {
            length "0..128";
          }
          description
           "The name of the Embedded Event Manager policy that was
            triggered because of an Embedded Event Manager event. The
            name must be a valid Embedded Event Manager policy name. 
            It must be in the form of a valid Posix filename.";
          smiv2:max-access "read-only";
          smiv2:oid "1.3.6.1.4.1.9.10.134.1.2.3.1.7";
        }

        leaf ceemHistoryPolicyExitStatus {
          type int32 {
            range "-2147483648..2147483647";
          }
          description
           "The exit status of the Embedded Event Manager policy
            execution.  This value corresponds to the Posix process 
            exit status.";
          reference
           "Posix 1003.1 Specification.";
          smiv2:max-access "read-only";
          smiv2:oid "1.3.6.1.4.1.9.10.134.1.2.3.1.8";
        }

        leaf ceemHistoryPolicyIntData1 {
          type int32 {
            range "-2147483648..2147483647";
          }
          description
           "Arbitrary integer data that the Embedded Event Manager policy
            can use. Use of this object is optional. If unused by
            a policy, this object will not be instantiated for 
            that policy.";
          smiv2:max-access "read-only";
          smiv2:oid "1.3.6.1.4.1.9.10.134.1.2.3.1.9";
        }

        leaf ceemHistoryPolicyIntData2 {
          type int32 {
            range "-2147483648..2147483647";
          }
          description
           "Arbitrary integer data that the Embedded Event Manager policy
            can use. Use of this object is optional. If unused by
            a policy, this object will not be instantiated for 
            that policy.";
          smiv2:max-access "read-only";
          smiv2:oid "1.3.6.1.4.1.9.10.134.1.2.3.1.10";
        }

        leaf ceemHistoryPolicyStrData {
          type snmp-framework:SnmpAdminString {
            length "0..255";
          }
          description
           "Arbitrary string data the Embedded Event Manager policy can
            use.  Use of this object is optional.  If unused by
            a policy, this object will not be instantiated for 
            that policy.";
          smiv2:max-access "read-only";
          smiv2:oid "1.3.6.1.4.1.9.10.134.1.2.3.1.11";
        }

        leaf ceemHistoryNotifyType {
          type CISCO-EMBEDDED-EVENT-MGR-MIB:NotifySource;
          description
           "The notification type that was sent from the Embedded Event
            Manager.  The valid values are server or policy.";
          smiv2:max-access "read-only";
          smiv2:oid "1.3.6.1.4.1.9.10.134.1.2.3.1.12";
        }

        leaf ceemHistoryEventType5 {
          type uint32;
          description
           "The type of Embedded Event Manager event which was
            detected. The value corresponds to an entry in the 
            ceemEventTable.";
          smiv2:max-access "read-only";
          smiv2:oid "1.3.6.1.4.1.9.10.134.1.2.3.1.13";
        }

        leaf ceemHistoryEventType6 {
          type uint32;
          description
           "The type of Embedded Event Manager event which was
            detected. The value corresponds to an entry in the 
            ceemEventTable.";
          smiv2:max-access "read-only";
          smiv2:oid "1.3.6.1.4.1.9.10.134.1.2.3.1.14";
        }

        leaf ceemHistoryEventType7 {
          type uint32;
          description
           "The type of Embedded Event Manager event which was
            detected. The value corresponds to an entry in the 
            ceemEventTable.";
          smiv2:max-access "read-only";
          smiv2:oid "1.3.6.1.4.1.9.10.134.1.2.3.1.15";
        }

        leaf ceemHistoryEventType8 {
          type uint32;
          description
           "The type of Embedded Event Manager event which was
            detected. The value corresponds to an entry in the 
            ceemEventTable.";
          smiv2:max-access "read-only";
          smiv2:oid "1.3.6.1.4.1.9.10.134.1.2.3.1.16";
        }
      }
    }

    container ceemRegisteredPolicyTable {
      description
       "A table of Embedded Event Manager policies registered on a system.
        The number of entries depends on the configuration of the system.  The 
        maximum number is implementation dependent.";
      smiv2:oid "1.3.6.1.4.1.9.10.134.1.3.1";

      list ceemRegisteredPolicyEntry {
        key "ceemRegisteredPolicyIndex";
        description
         "An entry in the table of Embedded Event Manager policies that are
          registered.  It provides up to four event types to support complex 
          event specifications that are triggered when multiple events are 
          published within a certain period of time.  A row in this table 
          cannot be created or deleted by SNMP operations on columns of the 
          table.";
        smiv2:oid "1.3.6.1.4.1.9.10.134.1.3.1.1";

        leaf ceemRegisteredPolicyIndex {
          type uint32;
          description
           "A monotonically increasing non-zero integer uniquely
            identifying a policy registration.  When it reaches the
            maximum value, the agent wraps the value back to 1 upon 
            receiving the next policy registration.";
          smiv2:max-access "not-accessible";
          smiv2:oid "1.3.6.1.4.1.9.10.134.1.3.1.1.1";
        }

        leaf ceemRegisteredPolicyName {
          type snmp-framework:SnmpAdminString {
            length "0..128";
          }
          description
           "The name of the Embedded Event Manager policy that was
            registered.  The name must be a valid Embedded Event 
            Manager policy name. It must be in the form of a valid 
            Posix filename.";
          smiv2:max-access "read-only";
          smiv2:oid "1.3.6.1.4.1.9.10.134.1.3.1.1.2";
        }

        leaf ceemRegisteredPolicyEventType1 {
          type uint32;
          description
           "The type of Embedded Event Manager event which was registered
            by the policy. The value corresponds to an entry in the
            ceemEventMapTable.";
          smiv2:max-access "read-only";
          smiv2:oid "1.3.6.1.4.1.9.10.134.1.3.1.1.3";
        }

        leaf ceemRegisteredPolicyEventType2 {
          type uint32;
          description
           "The type of Embedded Event Manager event which was registered
            by the policy. The value corresponds to an entry in the
            ceemEventMapTable.";
          smiv2:max-access "read-only";
          smiv2:oid "1.3.6.1.4.1.9.10.134.1.3.1.1.4";
        }

        leaf ceemRegisteredPolicyEventType3 {
          type uint32;
          description
           "The type of Embedded Event Manager event which was registered
            by the policy. The value corresponds to an entry in the
            ceemEventMapTable.";
          smiv2:max-access "read-only";
          smiv2:oid "1.3.6.1.4.1.9.10.134.1.3.1.1.5";
        }

        leaf ceemRegisteredPolicyEventType4 {
          type uint32;
          description
           "The type of Embedded Event Manager event which was registered
            by the policy. The value corresponds to an entry in the
            ceemEventMapTable.";
          smiv2:max-access "read-only";
          smiv2:oid "1.3.6.1.4.1.9.10.134.1.3.1.1.6";
        }

        leaf ceemRegisteredPolicyStatus {
          type enumeration {
            enum "enabled" {
              value "1";
            }
            enum "disabled" {
              value "2";
            }
          }
          description
           "This status indicates whether the policy is enabled or disabled.";
          smiv2:max-access "read-only";
          smiv2:oid "1.3.6.1.4.1.9.10.134.1.3.1.1.7";
        }

        leaf ceemRegisteredPolicyType {
          type enumeration {
            enum "user" {
              value "1";
            }
            enum "system" {
              value "2";
            }
          }
          description
           "This variable indicates whether this is a user or system policy.";
          smiv2:max-access "read-only";
          smiv2:oid "1.3.6.1.4.1.9.10.134.1.3.1.1.8";
        }

        leaf ceemRegisteredPolicyNotifFlag {
          type boolean;
          description
           "This flag indicates if an SNMP notification will be sent when
            policy is triggered.";
          smiv2:max-access "read-only";
          smiv2:oid "1.3.6.1.4.1.9.10.134.1.3.1.1.9";
        }

        leaf ceemRegisteredPolicyRegTime {
          type snmpv2-tc:DateAndTime;
          description
           "The time the policy was registered.  It is stored as a
            32-bit count of seconds since 0000 UTC, 1 January, 1970.";
          smiv2:max-access "read-only";
          smiv2:oid "1.3.6.1.4.1.9.10.134.1.3.1.1.10";
        }

        leaf ceemRegisteredPolicyEnabledTime {
          type snmpv2-tc:DateAndTime;
          description
           "The time the policy was last enabled.  It is stored as a
            32-bit count of seconds since 0000 UTC, 1 January, 1970.";
          smiv2:max-access "read-only";
          smiv2:oid "1.3.6.1.4.1.9.10.134.1.3.1.1.11";
        }

        leaf ceemRegisteredPolicyRunTime {
          type snmpv2-tc:DateAndTime;
          description
           "The last time the policy was run.  It is stored as a
            32-bit count of seconds since 0000 UTC, 1 January, 1970.";
          smiv2:max-access "read-only";
          smiv2:oid "1.3.6.1.4.1.9.10.134.1.3.1.1.12";
        }

        leaf ceemRegisteredPolicyRunCount {
          type yang:counter32;
          description
           "The number of times the policy has been run.";
          smiv2:max-access "read-only";
          smiv2:oid "1.3.6.1.4.1.9.10.134.1.3.1.1.13";
        }

        leaf ceemRegisteredPolicyEventType5 {
          type uint32;
          description
           "The type of Embedded Event Manager event which was registered
            by the policy. The value corresponds to an entry in the
            ceemEventMapTable.";
          smiv2:max-access "read-only";
          smiv2:oid "1.3.6.1.4.1.9.10.134.1.3.1.1.14";
        }

        leaf ceemRegisteredPolicyEventType6 {
          type uint32;
          description
           "The type of Embedded Event Manager event which was registered
            by the policy. The value corresponds to an entry in the
            ceemEventMapTable.";
          smiv2:max-access "read-only";
          smiv2:oid "1.3.6.1.4.1.9.10.134.1.3.1.1.15";
        }

        leaf ceemRegisteredPolicyEventType7 {
          type uint32;
          description
           "The type of Embedded Event Manager event which was registered
            by the policy. The value corresponds to an entry in the
            ceemEventMapTable.";
          smiv2:max-access "read-only";
          smiv2:oid "1.3.6.1.4.1.9.10.134.1.3.1.1.16";
        }

        leaf ceemRegisteredPolicyEventType8 {
          type uint32;
          description
           "The type of Embedded Event Manager event which was registered
            by the policy. The value corresponds to an entry in the
            ceemEventMapTable.";
          smiv2:max-access "read-only";
          smiv2:oid "1.3.6.1.4.1.9.10.134.1.3.1.1.17";
        }
      }
    }
  }

  notification cEventMgrServerEvent {
    description
     "This notification is sent by the Embedded Event Manager
      server after it has run a policy associated with the 
      event ceemHistoryEventType that was received.";
    smiv2:oid "1.3.6.1.4.1.9.10.134.0.1";

    container object-1 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType1 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType1";
        }
      }
    }

    container object-2 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType2 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType2";
        }
      }
    }

    container object-3 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType3 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType3";
        }
      }
    }

    container object-4 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType4 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType4";
        }
      }
    }

    container object-5 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyPath {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyPath";
        }
      }
    }

    container object-6 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyName {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyName";
        }
      }
    }

    container object-7 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyExitStatus {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyExitStatus";
        }
      }
    }
  }

  notification cEventMgrPolicyEvent {
    description
     "This notification is configured to be sent from within
      an Embedded Event Manager policy after an Embedded Event 
      Manager event ceemHistoryEventType has occurred.
      If one or more of the objects ceemHistoryPolicyIntData1, 
      ceemHistoryPolicyIntData2, and ceemHistoryPolicyStrData are
      not instantiated, then the varbind for the object(s) not 
      instantiated will contain the value 'noSuchInstance'.";
    smiv2:oid "1.3.6.1.4.1.9.10.134.0.2";

    container object-1 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType1 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType1";
        }
      }
    }

    container object-2 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType2 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType2";
        }
      }
    }

    container object-3 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType3 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType3";
        }
      }
    }

    container object-4 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryEventType4 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventType4";
        }
      }
    }

    container object-5 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyPath {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyPath";
        }
      }
    }

    container object-6 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyName {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyName";
        }
      }
    }

    container object-7 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyIntData1 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyIntData1";
        }
      }
    }

    container object-8 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyIntData2 {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyIntData2";
        }
      }
    }

    container object-9 {

      leaf ceemHistoryEventIndex {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryEventIndex";
        }
      }

      leaf ceemHistoryPolicyStrData {
        type leafref {
          path "/CISCO-EMBEDDED-EVENT-MGR-MIB:CISCO-EMBEDDED-EVENT-MGR-MIB/CISCO-EMBEDDED-EVENT-MGR-MIB:ceemHistoryEventTable/CISCO-EMBEDDED-EVENT-MGR-MIB:ceemHistoryEventEntry/CISCO-EMBEDDED-EVENT-MGR-MIB:ceemHistoryPolicyStrData";
        }
      }
    }
  }

  smiv2:alias "cEventMgrMIB" {
    smiv2:oid "1.3.6.1.4.1.9.10.134";
  }

  smiv2:alias "cEventMgrMIBNotif" {
    smiv2:oid "1.3.6.1.4.1.9.10.134.0";
  }

  smiv2:alias "cEventMgrMIBObjects" {
    smiv2:oid "1.3.6.1.4.1.9.10.134.1";
  }

  smiv2:alias "ceemEventMap" {
    smiv2:oid "1.3.6.1.4.1.9.10.134.1.1";
  }

  smiv2:alias "ceemHistory" {
    smiv2:oid "1.3.6.1.4.1.9.10.134.1.2";
  }

  smiv2:alias "ceemRegisteredPolicy" {
    smiv2:oid "1.3.6.1.4.1.9.10.134.1.3";
  }

  smiv2:alias "cEventMgrConformance" {
    smiv2:oid "1.3.6.1.4.1.9.10.134.3";
  }

  smiv2:alias "cEventMgrCompliances" {
    smiv2:oid "1.3.6.1.4.1.9.10.134.3.1";
  }

  smiv2:alias "cEventMgrGroups" {
    smiv2:oid "1.3.6.1.4.1.9.10.134.3.2";
  }

}
