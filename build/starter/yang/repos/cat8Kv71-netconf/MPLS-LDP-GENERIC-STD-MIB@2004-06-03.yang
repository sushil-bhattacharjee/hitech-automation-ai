/*
 * Generated by confdc --mib2yang-std
 * Source: mgmt/dmi/model/mib/src/MPLS-LDP-GENERIC-STD-MIB.mib
 */
/*
 * This YANG module has been generated by smidump 0.5.0:
 *
 *      smidump -f yang MPLS-LDP-GENERIC-STD-MIB
 *
 * Do not edit. Edit the source file instead!
 */

module MPLS-LDP-GENERIC-STD-MIB {

  namespace "urn:ietf:params:xml:ns:yang:smiv2:MPLS-LDP-GENERIC-STD-MIB";
  prefix MPLS-LDP-GENERIC-STD-MIB;

  import IF-MIB {
    prefix "if-mib";
  }

  import MPLS-LDP-STD-MIB {
    prefix "mpls-ldp";
  }

  import SNMPv2-TC {
    prefix "snmpv2-tc";
  }

  import ietf-yang-smiv2 {
    prefix "smiv2";
  }

  organization
   "Multiprotocol Label Switching (mpls)
    Working Group";

  contact
   "Joan Cucchiara (jcucchiara@mindspring.com)
    Marconi Communications, Inc.
    
    Hans Sjostrand (hans@ipunplugged.com)
    ipUnplugged
    
    
    James V. Luciani (james_luciani@mindspring.com)
    Marconi Communications, Inc.
    
    Working Group Chairs:
    George Swallow,   email: swallow@cisco.com
    Loa Andersson,    email: loa@pi.se
    
    MPLS Working Group, email: mpls@uu.net";

  description
   "Copyright (C) The Internet Society (year). The
    initial version of this MIB module was published
    in RFC 3815. For full legal notices see the RFC
    itself or see:
    http://www.ietf.org/copyrights/ianamib.html
    
    This MIB contains managed object definitions for
    configuring and monitoring the Multiprotocol Label
    Switching (MPLS), Label Distribution Protocol (LDP),
    utilizing ethernet as the Layer 2 media.";

  revision 2004-06-03 {
    description
     "Initial version published as part of RFC 3815.";
  }


  container MPLS-LDP-GENERIC-STD-MIB {
    config false;

    container mplsLdpEntityGenericLRTable {
      description
       "The MPLS LDP Entity Generic Label Range (LR)
        Table.
        
        The purpose of this table is to provide a mechanism
        for configurating a contiguous range of generic labels,
        or a 'label range' for LDP Entities.
        
        LDP Entities which use Generic Labels must have at least
        one entry in this table.  In other words, this table
        'extends' the mpldLdpEntityTable for Generic Labels.";
      smiv2:oid "1.3.6.1.2.1.10.166.7.1.1.1";

      list mplsLdpEntityGenericLREntry {
        key "mplsLdpEntityLdpId mplsLdpEntityIndex mplsLdpEntityGenericLRMin mplsLdpEntityGenericLRMax";
        description
         "A row in the LDP Entity Generic Label
          Range (LR) Table.  One entry in this table contains
          information on a single range of labels
          represented by the configured Upper and Lower
          Bounds pairs.  NOTE: there is NO corresponding
          LDP message which relates to the information
          in this table, however, this table does provide
          a way for a user to 'reserve' a generic label
          range.
          
          NOTE:  The ranges for a specific LDP Entity
          are UNIQUE and non-overlapping.
          
          A row will not be created unless a unique and
          non-overlapping range is specified.";
        smiv2:oid "1.3.6.1.2.1.10.166.7.1.1.1.1";

        leaf mplsLdpEntityLdpId {
          type leafref {
            path "/mpls-ldp:MPLS-LDP-STD-MIB/mpls-ldp:mplsLdpEntityTable/mpls-ldp:mplsLdpEntityEntry/mpls-ldp:mplsLdpEntityLdpId";
          }
        }

        leaf mplsLdpEntityIndex {
          type leafref {
            path "/mpls-ldp:MPLS-LDP-STD-MIB/mpls-ldp:mplsLdpEntityTable/mpls-ldp:mplsLdpEntityEntry/mpls-ldp:mplsLdpEntityIndex";
          }
        }

        leaf mplsLdpEntityGenericLRMin {
          type uint32 {
            range "0..1048575";
          }
          description
           "The minimum label configured for this range.";
          smiv2:max-access "not-accessible";
          smiv2:oid "1.3.6.1.2.1.10.166.7.1.1.1.1.1";
        }

        leaf mplsLdpEntityGenericLRMax {
          type uint32 {
            range "0..1048575";
          }
          description
           "The maximum label configured for this range.";
          smiv2:max-access "not-accessible";
          smiv2:oid "1.3.6.1.2.1.10.166.7.1.1.1.1.2";
        }

        leaf mplsLdpEntityGenericLabelSpace {
          type enumeration {
            enum "perPlatform" {
              value "1";
            }
            enum "perInterface" {
              value "2";
            }
          }
          description
           "This value of this object is perPlatform(1), then
            this means that the label space type is
            per platform.
            
            If this object is perInterface(2), then this
            means that the label space type is per Interface.";
          reference
           "RFC3036, LDP Specification, Section 2.2.1,
            Label Spaces.";
          smiv2:defval "perPlatform";
          smiv2:max-access "read-write";
          smiv2:oid "1.3.6.1.2.1.10.166.7.1.1.1.1.3";
        }

        leaf mplsLdpEntityGenericIfIndexOrZero {
          type if-mib:InterfaceIndexOrZero;
          description
           "This value represents either the InterfaceIndex of
            the 'ifLayer' where these Generic Label would be created,
            
            
            or 0 (zero).  The value of zero means that the
            InterfaceIndex is not known.
            
            However, if the InterfaceIndex is known,
            then it must be represented by this value.
            
            If an InterfaceIndex becomes known, then the
            network management entity (e.g., SNMP agent) responsible
            for this object MUST change the value from 0 (zero) to the
            value of the InterfaceIndex.";
          smiv2:max-access "read-write";
          smiv2:oid "1.3.6.1.2.1.10.166.7.1.1.1.1.4";
        }

        leaf mplsLdpEntityGenericLRStorageType {
          type snmpv2-tc:StorageType;
          description
           "The storage type for this conceptual row.
            Conceptual rows having the value 'permanent(4)'
            need not allow write-access to any columnar
            objects in the row.";
          smiv2:defval "nonVolatile";
          smiv2:max-access "read-write";
          smiv2:oid "1.3.6.1.2.1.10.166.7.1.1.1.1.5";
        }

        leaf mplsLdpEntityGenericLRRowStatus {
          type snmpv2-tc:RowStatus;
          description
           "The status of this conceptual row.  All writable
            objects in this row may be modified at any time,
            however, as described in  detail in the section
            entitled, 'Changing Values After Session
            Establishment', and again described in the
            DESCRIPTION clause of the mplsLdpEntityAdminStatus object,
            if a session has been initiated with a Peer,
            changing objects in this table will
            wreak havoc with the session and interrupt traffic.
            To repeat again:  the recommended procedure is
            to set the mplsLdpEntityAdminStatus to
            down, thereby explicitly causing a
            session to be torn down. Then, change objects
            in this entry, then set the mplsLdpEntityAdminStatus
            to enable which enables a new session to be initiated.
            
            There must exist at least one entry in this
            table for every LDP Entity that has a
            generic label configured.";
          smiv2:max-access "read-write";
          smiv2:oid "1.3.6.1.2.1.10.166.7.1.1.1.1.6";
        }
      }
    }
  }

  smiv2:alias "mplsLdpGenericStdMIB" {
    smiv2:oid "1.3.6.1.2.1.10.166.7";
  }

  smiv2:alias "mplsLdpGenericObjects" {
    smiv2:oid "1.3.6.1.2.1.10.166.7.1";
  }

  smiv2:alias "mplsLdpEntityGenericObjects" {
    smiv2:oid "1.3.6.1.2.1.10.166.7.1.1";
  }

  smiv2:alias "mplsLdpGenericConformance" {
    smiv2:oid "1.3.6.1.2.1.10.166.7.2";
  }

  smiv2:alias "mplsLdpGenericGroups" {
    smiv2:oid "1.3.6.1.2.1.10.166.7.2.1";
  }

  smiv2:alias "mplsLdpGenericCompliances" {
    smiv2:oid "1.3.6.1.2.1.10.166.7.2.2";
  }

}
