/*
 * Generated by confdc --mib2yang-std
 * Source: mgmt/dmi/model/mib/src/DS3-MIB.mib
 */
/*
 * This YANG module has been generated by smidump 0.5.0:
 *
 *      smidump -f yang DS3-MIB
 *
 * Do not edit. Edit the source file instead!
 */

module DS3-MIB {

  namespace "urn:ietf:params:xml:ns:yang:smiv2:DS3-MIB";
  prefix DS3-MIB;

  import IF-MIB {
    prefix "if-mib";
  }

  import PerfHist-TC-MIB {
    prefix "perfhist-tc";
  }

  import SNMPv2-TC {
    prefix "snmpv2-tc";
  }

  import ietf-yang-smiv2 {
    prefix "smiv2";
  }

  import ietf-yang-types {
    prefix "yang";
  }

  organization
   "IETF Trunk MIB Working Group";

  contact
   "        David Fowler
    
    Postal: Newbridge Networks Corporation
            600 March Road
            Kanata, Ontario, Canada K2K 2E6
    
            Tel: +1 613 591 3600
            Fax: +1 613 599 3667
    
    E-mail: davef@newbridge.com";

  description
   "The is the MIB module that describes
    DS3 and E3 interfaces objects.";

  revision 1998-08-01 {
    description
     "[Revision added by libsmi due to a LAST-UPDATED clause.]";
  }


  container DS3-MIB {
    config false;

    container dsx3ConfigTable {
      description
       "The DS3/E3 Configuration table.";
      smiv2:oid "1.3.6.1.2.1.10.30.5";

      list dsx3ConfigEntry {
        key "dsx3LineIndex";
        description
         "An entry in the DS3/E3 Configuration table.";
        smiv2:oid "1.3.6.1.2.1.10.30.5.1";

        leaf dsx3LineIndex {
          type if-mib:InterfaceIndex;
          description
           "This object should be made equal to ifIndex.  The
            next paragraph describes its previous usage.
            Making the object equal to ifIndex allows propoer
            use of ifStackTable.
            
            Previously, this object was the identifier of a
            DS3/E3 Interface on a managed device.  If there is
            an ifEntry that is directly associated with this
            and only this DS3/E3 interface, it should have the
            same value as ifIndex.  Otherwise, number the
            dsx3LineIndices with an unique identifier
            following the rules of choosing a number that is
            greater than ifNumber and numbering the inside
            interfaces (e.g., equipment side) with even
            numbers and outside interfaces (e.g, network side)
            with odd numbers.";
          smiv2:max-access "read-only";
          smiv2:oid "1.3.6.1.2.1.10.30.5.1.1";
        }

        leaf dsx3IfIndex {
          type if-mib:InterfaceIndex;
          status deprecated;
          description
           "This value for this object is equal to the value
            of ifIndex from the Interfaces table of MIB II
            (RFC 1213).";
          smiv2:max-access "read-only";
          smiv2:oid "1.3.6.1.2.1.10.30.5.1.2";
        }

        leaf dsx3TimeElapsed {
          type int32 {
            range "0..899";
          }
          description
           "The number of seconds that have elapsed since the
            beginning of the near end current error-
            measurement period.  If, for some reason, such as
            an adjustment in the system's time-of-day clock,
            the current interval exceeds the maximum value,
            the agent will return the maximum value.";
          smiv2:max-access "read-only";
          smiv2:oid "1.3.6.1.2.1.10.30.5.1.3";
        }

        leaf dsx3ValidIntervals {
          type int32 {
            range "0..96";
          }
          description
           "The number of previous near end intervals for
            which data was collected.  The value will be
            96 unless the interface was brought online within
            the last 24 hours, in which case the value will be
            the number of complete 15 minute near end
            intervals since the interface has been online.  In
            the case where the agent is a proxy, it is
            possible that some intervals are unavailable.  In
            this case, this interval is the maximum interval
            number for which data is available.";
          smiv2:max-access "read-only";
          smiv2:oid "1.3.6.1.2.1.10.30.5.1.4";
        }

        leaf dsx3LineType {
          type enumeration {
            enum "dsx3other" {
              value "1";
            }
            enum "dsx3M23" {
              value "2";
            }
            enum "dsx3SYNTRAN" {
              value "3";
            }
            enum "dsx3CbitParity" {
              value "4";
            }
            enum "dsx3ClearChannel" {
              value "5";
            }
            enum "e3other" {
              value "6";
            }
            enum "e3Framed" {
              value "7";
            }
            enum "e3Plcp" {
              value "8";
            }
          }
          description
           "This variable indicates the variety of DS3 C-bit
            or E3 application implementing this interface. The
            type of interface affects the interpretation of
            the usage and error statistics.  The rate of DS3
            is 44.736 Mbps and E3 is 34.368 Mbps.  The
            dsx3ClearChannel value means that the C-bits are
            not used except for sending/receiving AIS.
            The values, in sequence, describe:
            
            TITLE:            SPECIFICATION:
            dsx3M23            ANSI T1.107-1988 [9]
            dsx3SYNTRAN        ANSI T1.107-1988 [9]
            dsx3CbitParity     ANSI T1.107a-1990 [9a]
            dsx3ClearChannel   ANSI T1.102-1987 [8]
            e3Framed           CCITT G.751 [12]
            e3Plcp             ETSI T/NA(91)18 [13].";
          smiv2:max-access "read-write";
          smiv2:oid "1.3.6.1.2.1.10.30.5.1.5";
        }

        leaf dsx3LineCoding {
          type enumeration {
            enum "dsx3Other" {
              value "1";
            }
            enum "dsx3B3ZS" {
              value "2";
            }
            enum "e3HDB3" {
              value "3";
            }
          }
          description
           "This variable describes the variety of Zero Code
            Suppression used on this interface, which in turn
            affects a number of its characteristics.
            
            dsx3B3ZS and e3HDB3 refer to the use of specified
            patterns of normal bits and bipolar violations
            which are used to replace sequences of zero bits
            of a specified length.";
          smiv2:max-access "read-write";
          smiv2:oid "1.3.6.1.2.1.10.30.5.1.6";
        }

        leaf dsx3SendCode {
          type enumeration {
            enum "dsx3SendNoCode" {
              value "1";
            }
            enum "dsx3SendLineCode" {
              value "2";
            }
            enum "dsx3SendPayloadCode" {
              value "3";
            }
            enum "dsx3SendResetCode" {
              value "4";
            }
            enum "dsx3SendDS1LoopCode" {
              value "5";
            }
            enum "dsx3SendTestPattern" {
              value "6";
            }
          }
          description
           "This variable indicates what type of code is
            being sent across the DS3/E3 interface by the
            device.  (These are optional for E3 interfaces.)
            Setting this variable causes the interface to
            begin sending the code requested.
            The values mean:
            
               dsx3SendNoCode
                   sending looped or normal data
            
               dsx3SendLineCode
                   sending a request for a line loopback
            
               dsx3SendPayloadCode
                   sending a request for a payload loopback
                   (i.e., all DS1/E1s in a DS3/E3 frame)
            
               dsx3SendResetCode
                   sending a loopback deactivation request
            
               dsx3SendDS1LoopCode
                   requesting to loopback a particular DS1/E1
                   within a DS3/E3 frame.  The DS1/E1 is
                   indicated in dsx3Ds1ForRemoteLoop.
            
               dsx3SendTestPattern
                   sending a test pattern.";
          smiv2:max-access "read-write";
          smiv2:oid "1.3.6.1.2.1.10.30.5.1.7";
        }

        leaf dsx3CircuitIdentifier {
          type snmpv2-tc:DisplayString {
            length "0..255";
          }
          description
           "This variable contains the transmission vendor's
            circuit identifier, for the purpose of
            facilitating troubleshooting.";
          smiv2:max-access "read-write";
          smiv2:oid "1.3.6.1.2.1.10.30.5.1.8";
        }

        leaf dsx3LoopbackConfig {
          type enumeration {
            enum "dsx3NoLoop" {
              value "1";
            }
            enum "dsx3PayloadLoop" {
              value "2";
            }
            enum "dsx3LineLoop" {
              value "3";
            }
            enum "dsx3OtherLoop" {
              value "4";
            }
            enum "dsx3InwardLoop" {
              value "5";
            }
            enum "dsx3DualLoop" {
              value "6";
            }
          }
          description
           "This variable represents the desired loopback
            configuration of the DS3/E3 interface.
            
            The values mean:
            
            dsx3NoLoop
              Not in the loopback state.  A device that is
              not capable of performing a loopback on
              the interface shall always return this as
              its value.
            
            dsx3PayloadLoop
              The received signal at this interface is looped
              through the device.  Typically the received signal
              is looped back for retransmission after it has
              passed through the device's framing function.
            
            dsx3LineLoop
              The received signal at this interface does not
              go through the device (minimum penetration) but
              is looped back out.
            
            dsx3OtherLoop
              Loopbacks that are not defined here.
            
            dsx3InwardLoop
              The sent signal at this interface is looped back
              through the device.
            
            dsx3DualLoop
              Both dsx1LineLoop and dsx1InwardLoop will be
              active simultaneously.";
          smiv2:max-access "read-write";
          smiv2:oid "1.3.6.1.2.1.10.30.5.1.9";
        }

        leaf dsx3LineStatus {
          type int32 {
            range "1..4095";
          }
          description
           "This variable indicates the Line Status of the
            interface.  It contains loopback state information
            and failure state information.  The dsx3LineStatus
            is a bit map represented as a sum, therefore, it
            can represent multiple failures and a loopback
            (see dsx3LoopbackConfig object for the type of
            loopback) simultaneously.  The dsx3NoAlarm must be
            set if and only if no other flag is set.
            
            If the dsx3loopbackState bit is set, the loopback
            in effect can be determined from the
            dsx3loopbackConfig object.
            The various bit positions are:
            1     dsx3NoAlarm         No alarm present
            2     dsx3RcvRAIFailure   Receiving Yellow/Remote
                             Alarm Indication
            4     dsx3XmitRAIAlarm    Transmitting Yellow/Remote
                             Alarm Indication
            8     dsx3RcvAIS          Receiving AIS failure state
            16     dsx3XmitAIS         Transmitting AIS
            32     dsx3LOF             Receiving LOF failure state
            64     dsx3LOS             Receiving LOS failure state
            128     dsx3LoopbackState   Looping the received signal
            256     dsx3RcvTestCode     Receiving a Test Pattern
            512     dsx3OtherFailure    any line status not defined
                             here
            1024     dsx3UnavailSigState Near End in Unavailable Signal
                             State
            2048     dsx3NetEquipOOS     Carrier Equipment Out of Service";
          smiv2:max-access "read-only";
          smiv2:oid "1.3.6.1.2.1.10.30.5.1.10";
        }

        leaf dsx3TransmitClockSource {
          type enumeration {
            enum "loopTiming" {
              value "1";
            }
            enum "localTiming" {
              value "2";
            }
            enum "throughTiming" {
              value "3";
            }
          }
          description
           "The source of Transmit Clock.
            
            loopTiming indicates that the recovered receive clock
            is used as the transmit clock.
            
            localTiming indicates that a local clock source is used
            or that an external clock is attached to the box
            containing the interface.
            
            throughTiming indicates that transmit clock is derived
            from the recovered receive clock of another DS3
            interface.";
          smiv2:max-access "read-write";
          smiv2:oid "1.3.6.1.2.1.10.30.5.1.11";
        }

        leaf dsx3InvalidIntervals {
          type int32 {
            range "0..96";
          }
          description
           "The number of intervals in the range from 0 to
            dsx3ValidIntervals for which no data is
            available.  This object will typically be zero
            except in cases where the data for some intervals
            are not available (e.g., in proxy situations).";
          smiv2:max-access "read-only";
          smiv2:oid "1.3.6.1.2.1.10.30.5.1.12";
        }

        leaf dsx3LineLength {
          type int32 {
            range "0..64000";
          }
          units "meters";
          description
           "The length of the ds3 line in meters.  This
            object provides information for line build out
            circuitry if it exists and can use this object to
            adjust the line build out.";
          smiv2:max-access "read-write";
          smiv2:oid "1.3.6.1.2.1.10.30.5.1.13";
        }

        leaf dsx3LineStatusLastChange {
          type yang:timestamp;
          description
           "The value of MIB II's sysUpTime object at the
            time this DS3/E3 entered its current line status
            state.  If the current state was entered prior to
            the last re-initialization of the proxy-agent,
            then this object contains a zero value.";
          smiv2:max-access "read-only";
          smiv2:oid "1.3.6.1.2.1.10.30.5.1.14";
        }

        leaf dsx3LineStatusChangeTrapEnable {
          type enumeration {
            enum "enabled" {
              value "1";
            }
            enum "disabled" {
              value "2";
            }
          }
          description
           "Indicates whether dsx3LineStatusChange traps
            should be generated for this interface.";
          smiv2:defval "disabled";
          smiv2:max-access "read-write";
          smiv2:oid "1.3.6.1.2.1.10.30.5.1.15";
        }

        leaf dsx3LoopbackStatus {
          type int32 {
            range "1..127";
          }
          description
           "This variable represents the current state of the
            loopback on the DS3 interface.  It contains
            information about loopbacks established by a
            manager and remotely from the far end.
            
            The dsx3LoopbackStatus is a bit map represented as
            a sum, therefore is can represent multiple
            loopbacks simultaneously.
            
            The various bit positions are:
             1  dsx3NoLoopback
             2  dsx3NearEndPayloadLoopback
             4  dsx3NearEndLineLoopback
             8  dsx3NearEndOtherLoopback
            16  dsx3NearEndInwardLoopback
            32  dsx3FarEndPayloadLoopback
            64  dsx3FarEndLineLoopback";
          smiv2:max-access "read-only";
          smiv2:oid "1.3.6.1.2.1.10.30.5.1.16";
        }

        leaf dsx3Channelization {
          type enumeration {
            enum "disabled" {
              value "1";
            }
            enum "enabledDs1" {
              value "2";
            }
            enum "enabledDs2" {
              value "3";
            }
          }
          description
           "Indicates whether this ds3/e3 is channelized or
            unchannelized.  The value of enabledDs1 indicates
            that this is a DS3 channelized into DS1s.  The
            value of enabledDs3 indicated that this is a DS3
            channelized into DS2s.  Setting this object will
            cause the creation or deletion of DS2 or DS1
            entries in the ifTable.  ";
          smiv2:max-access "read-write";
          smiv2:oid "1.3.6.1.2.1.10.30.5.1.17";
        }

        leaf dsx3Ds1ForRemoteLoop {
          type int32 {
            range "0..29";
          }
          description
           "Indicates which ds1/e1 on this ds3/e3 will be
            indicated in the remote ds1 loopback request.  A
            value of 0 means no DS1 will be looped.  A value
            of 29 means all ds1s/e1s will be looped.";
          smiv2:max-access "read-write";
          smiv2:oid "1.3.6.1.2.1.10.30.5.1.18";
        }
      }
    }

    container dsx3CurrentTable {
      description
       "The DS3/E3 current table contains various
        statistics being collected for the current 15
        minute interval.";
      smiv2:oid "1.3.6.1.2.1.10.30.6";

      list dsx3CurrentEntry {
        key "dsx3CurrentIndex";
        description
         "An entry in the DS3/E3 Current table.";
        smiv2:oid "1.3.6.1.2.1.10.30.6.1";

        leaf dsx3CurrentIndex {
          type if-mib:InterfaceIndex;
          description
           "The index value which uniquely identifies the
            DS3/E3 interface to which this entry is
            applicable.  The interface identified by a
            particular value of this index is the same
            interface as identified by the same value an
            dsx3LineIndex object instance.";
          smiv2:max-access "read-only";
          smiv2:oid "1.3.6.1.2.1.10.30.6.1.1";
        }

        leaf dsx3CurrentPESs {
          type perfhist-tc:PerfCurrentCount;
          description
           "The counter associated with the number of P-bit
            Errored Seconds.";
          smiv2:max-access "read-only";
          smiv2:oid "1.3.6.1.2.1.10.30.6.1.2";
        }

        leaf dsx3CurrentPSESs {
          type perfhist-tc:PerfCurrentCount;
          description
           "The counter associated with the number of P-bit
            Severely Errored Seconds.";
          smiv2:max-access "read-only";
          smiv2:oid "1.3.6.1.2.1.10.30.6.1.3";
        }

        leaf dsx3CurrentSEFSs {
          type perfhist-tc:PerfCurrentCount;
          description
           "The counter associated with the number of
            Severely Errored Framing Seconds.";
          smiv2:max-access "read-only";
          smiv2:oid "1.3.6.1.2.1.10.30.6.1.4";
        }

        leaf dsx3CurrentUASs {
          type perfhist-tc:PerfCurrentCount;
          description
           "The counter associated with the number of
            Unavailable Seconds.";
          smiv2:max-access "read-only";
          smiv2:oid "1.3.6.1.2.1.10.30.6.1.5";
        }

        leaf dsx3CurrentLCVs {
          type perfhist-tc:PerfCurrentCount;
          description
           "The counter associated with the number of Line
            Coding Violations.";
          smiv2:max-access "read-only";
          smiv2:oid "1.3.6.1.2.1.10.30.6.1.6";
        }

        leaf dsx3CurrentPCVs {
          type perfhist-tc:PerfCurrentCount;
          description
           "The counter associated with the number of P-bit
            Coding Violations.";
          smiv2:max-access "read-only";
          smiv2:oid "1.3.6.1.2.1.10.30.6.1.7";
        }

        leaf dsx3CurrentLESs {
          type perfhist-tc:PerfCurrentCount;
          description
           "The number of Line Errored Seconds.";
          smiv2:max-access "read-only";
          smiv2:oid "1.3.6.1.2.1.10.30.6.1.8";
        }

        leaf dsx3CurrentCCVs {
          type perfhist-tc:PerfCurrentCount;
          description
           "The number of C-bit Coding Violations.";
          smiv2:max-access "read-only";
          smiv2:oid "1.3.6.1.2.1.10.30.6.1.9";
        }

        leaf dsx3CurrentCESs {
          type perfhist-tc:PerfCurrentCount;
          description
           "The number of C-bit Errored Seconds.";
          smiv2:max-access "read-only";
          smiv2:oid "1.3.6.1.2.1.10.30.6.1.10";
        }

        leaf dsx3CurrentCSESs {
          type perfhist-tc:PerfCurrentCount;
          description
           "The number of C-bit Severely Errored Seconds.";
          smiv2:max-access "read-only";
          smiv2:oid "1.3.6.1.2.1.10.30.6.1.11";
        }
      }
    }

    container dsx3IntervalTable {
      description
       "The DS3/E3 Interval Table contains various
        statistics collected by each DS3/E3 Interface over
        the previous 24 hours of operation.  The past 24
        hours are broken into 96 completed 15 minute
        intervals.  Each row in this table represents one
        such interval (identified by dsx3IntervalNumber)
        and for one specific interface (identifed by
        dsx3IntervalIndex).";
      smiv2:oid "1.3.6.1.2.1.10.30.7";

      list dsx3IntervalEntry {
        key "dsx3IntervalIndex dsx3IntervalNumber";
        description
         "An entry in the DS3/E3 Interval table.";
        smiv2:oid "1.3.6.1.2.1.10.30.7.1";

        leaf dsx3IntervalIndex {
          type if-mib:InterfaceIndex;
          description
           "The index value which uniquely identifies the
            DS3/E3 interface to which this entry is
            applicable.  The interface identified by a
            particular value of this index is the same
            interface as identified by the same value an
            dsx3LineIndex object instance.";
          smiv2:max-access "read-only";
          smiv2:oid "1.3.6.1.2.1.10.30.7.1.1";
        }

        leaf dsx3IntervalNumber {
          type int32 {
            range "1..96";
          }
          description
           "A number between 1 and 96, where 1 is the most
            recently completed 15 minute interval and 96 is
            the 15 minutes interval completed 23 hours and 45
            minutes prior to interval 1.";
          smiv2:max-access "read-only";
          smiv2:oid "1.3.6.1.2.1.10.30.7.1.2";
        }

        leaf dsx3IntervalPESs {
          type perfhist-tc:PerfIntervalCount;
          description
           "The counter associated with the number of P-bit
            Errored Seconds.";
          smiv2:max-access "read-only";
          smiv2:oid "1.3.6.1.2.1.10.30.7.1.3";
        }

        leaf dsx3IntervalPSESs {
          type perfhist-tc:PerfIntervalCount;
          description
           "The counter associated with the number of P-bit
            Severely Errored Seconds.";
          smiv2:max-access "read-only";
          smiv2:oid "1.3.6.1.2.1.10.30.7.1.4";
        }

        leaf dsx3IntervalSEFSs {
          type perfhist-tc:PerfIntervalCount;
          description
           "The counter associated with the number of
            Severely Errored Framing Seconds.";
          smiv2:max-access "read-only";
          smiv2:oid "1.3.6.1.2.1.10.30.7.1.5";
        }

        leaf dsx3IntervalUASs {
          type perfhist-tc:PerfIntervalCount;
          description
           "The counter associated with the number of
            Unavailable Seconds.  This object may decrease if
            the occurance of unavailable seconds occurs across
            an inteval boundary.";
          smiv2:max-access "read-only";
          smiv2:oid "1.3.6.1.2.1.10.30.7.1.6";
        }

        leaf dsx3IntervalLCVs {
          type perfhist-tc:PerfIntervalCount;
          description
           "The counter associated with the number of Line
            Coding Violations.";
          smiv2:max-access "read-only";
          smiv2:oid "1.3.6.1.2.1.10.30.7.1.7";
        }

        leaf dsx3IntervalPCVs {
          type perfhist-tc:PerfIntervalCount;
          description
           "The counter associated with the number of P-bit
            Coding Violations.";
          smiv2:max-access "read-only";
          smiv2:oid "1.3.6.1.2.1.10.30.7.1.8";
        }

        leaf dsx3IntervalLESs {
          type perfhist-tc:PerfIntervalCount;
          description
           "The number of Line Errored  Seconds  (BPVs  or
            illegal  zero  sequences).";
          smiv2:max-access "read-only";
          smiv2:oid "1.3.6.1.2.1.10.30.7.1.9";
        }

        leaf dsx3IntervalCCVs {
          type perfhist-tc:PerfIntervalCount;
          description
           "The number of C-bit Coding Violations.";
          smiv2:max-access "read-only";
          smiv2:oid "1.3.6.1.2.1.10.30.7.1.10";
        }

        leaf dsx3IntervalCESs {
          type perfhist-tc:PerfIntervalCount;
          description
           "The number of C-bit Errored Seconds.";
          smiv2:max-access "read-only";
          smiv2:oid "1.3.6.1.2.1.10.30.7.1.11";
        }

        leaf dsx3IntervalCSESs {
          type perfhist-tc:PerfIntervalCount;
          description
           "The number of C-bit Severely Errored Seconds.";
          smiv2:max-access "read-only";
          smiv2:oid "1.3.6.1.2.1.10.30.7.1.12";
        }

        leaf dsx3IntervalValidData {
          type boolean;
          description
           "This variable indicates if the data for this
            interval is valid.";
          smiv2:max-access "read-only";
          smiv2:oid "1.3.6.1.2.1.10.30.7.1.13";
        }
      }
    }

    container dsx3TotalTable {
      description
       "The DS3/E3 Total Table contains the cumulative
        sum of the various statistics for the 24 hour
        period preceding the current interval.";
      smiv2:oid "1.3.6.1.2.1.10.30.8";

      list dsx3TotalEntry {
        key "dsx3TotalIndex";
        description
         "An entry in the DS3/E3 Total table.";
        smiv2:oid "1.3.6.1.2.1.10.30.8.1";

        leaf dsx3TotalIndex {
          type if-mib:InterfaceIndex;
          description
           "The index value which uniquely identifies the
            DS3/E3 interface to which this entry is
            applicable.  The interface identified by a
            particular value of this index is the same
            interface as identified by the same value an
            dsx3LineIndex object instance.";
          smiv2:max-access "read-only";
          smiv2:oid "1.3.6.1.2.1.10.30.8.1.1";
        }

        leaf dsx3TotalPESs {
          type perfhist-tc:PerfTotalCount;
          description
           "The counter associated with the number of P-bit
            Errored Seconds, encountered by a DS3 interface in
            the previous 24 hour interval. Invalid 15 minute
            intervals count as 0.";
          smiv2:max-access "read-only";
          smiv2:oid "1.3.6.1.2.1.10.30.8.1.2";
        }

        leaf dsx3TotalPSESs {
          type perfhist-tc:PerfTotalCount;
          description
           "The counter associated with the number of P-bit
            Severely Errored Seconds, encountered by a DS3
            interface in the previous 24 hour interval.
            Invalid 15 minute intervals count as 0.";
          smiv2:max-access "read-only";
          smiv2:oid "1.3.6.1.2.1.10.30.8.1.3";
        }

        leaf dsx3TotalSEFSs {
          type perfhist-tc:PerfTotalCount;
          description
           "The counter associated with the number of
            Severely Errored Framing Seconds, encountered by a
            DS3/E3 interface in the previous 24 hour interval.
            Invalid 15 minute intervals count as 0.";
          smiv2:max-access "read-only";
          smiv2:oid "1.3.6.1.2.1.10.30.8.1.4";
        }

        leaf dsx3TotalUASs {
          type perfhist-tc:PerfTotalCount;
          description
           "The counter associated with the number of
            Unavailable Seconds, encountered by a DS3
            interface in the previous 24 hour interval.
            
            Invalid 15 minute intervals count as 0.";
          smiv2:max-access "read-only";
          smiv2:oid "1.3.6.1.2.1.10.30.8.1.5";
        }

        leaf dsx3TotalLCVs {
          type perfhist-tc:PerfTotalCount;
          description
           "The counter associated with the number of Line
            Coding Violations encountered by a DS3/E3
            interface in the previous 24 hour interval.
            Invalid 15 minute intervals count as 0.";
          smiv2:max-access "read-only";
          smiv2:oid "1.3.6.1.2.1.10.30.8.1.6";
        }

        leaf dsx3TotalPCVs {
          type perfhist-tc:PerfTotalCount;
          description
           "The counter associated with the number of P-bit
            Coding Violations, encountered by a DS3 interface
            in the previous 24 hour interval. Invalid 15
            minute intervals count as 0.";
          smiv2:max-access "read-only";
          smiv2:oid "1.3.6.1.2.1.10.30.8.1.7";
        }

        leaf dsx3TotalLESs {
          type perfhist-tc:PerfTotalCount;
          description
           "The number of Line Errored  Seconds  (BPVs  or
            illegal  zero  sequences) encountered by a DS3/E3
            interface in the previous 24 hour interval.
            Invalid 15 minute intervals count as 0.";
          smiv2:max-access "read-only";
          smiv2:oid "1.3.6.1.2.1.10.30.8.1.8";
        }

        leaf dsx3TotalCCVs {
          type perfhist-tc:PerfTotalCount;
          description
           "The number of C-bit Coding Violations encountered
            by a DS3 interface in the previous 24 hour
            interval. Invalid 15 minute intervals count as 0.";
          smiv2:max-access "read-only";
          smiv2:oid "1.3.6.1.2.1.10.30.8.1.9";
        }

        leaf dsx3TotalCESs {
          type perfhist-tc:PerfTotalCount;
          description
           "The number of C-bit Errored Seconds encountered
            by a DS3 interface in the previous 24 hour
            interval. Invalid 15 minute intervals count as 0.";
          smiv2:max-access "read-only";
          smiv2:oid "1.3.6.1.2.1.10.30.8.1.10";
        }

        leaf dsx3TotalCSESs {
          type perfhist-tc:PerfTotalCount;
          description
           "The number of C-bit Severely Errored Seconds
            encountered by a DS3 interface in the previous 24
            hour interval. Invalid 15 minute intervals count
            as 0.";
          smiv2:max-access "read-only";
          smiv2:oid "1.3.6.1.2.1.10.30.8.1.11";
        }
      }
    }

    container dsx3FarEndConfigTable {
      description
       "The DS3 Far End Configuration Table contains
        configuration information reported in the C-bits
        from the remote end.";
      smiv2:oid "1.3.6.1.2.1.10.30.9";

      list dsx3FarEndConfigEntry {
        key "dsx3FarEndLineIndex";
        description
         "An entry in the DS3 Far End Configuration table.";
        smiv2:oid "1.3.6.1.2.1.10.30.9.1";

        leaf dsx3FarEndLineIndex {
          type if-mib:InterfaceIndex;
          description
           "The index value which uniquely identifies the DS3
            interface to which this entry is applicable.  The
            interface identified by a particular value of this
            index is the same interface as identified by the
            same value an dsx3LineIndex object instance.";
          smiv2:max-access "read-only";
          smiv2:oid "1.3.6.1.2.1.10.30.9.1.1";
        }

        leaf dsx3FarEndEquipCode {
          type snmpv2-tc:DisplayString {
            length "0..10";
          }
          description
           "This is the Far End Equipment Identification code
            that describes the specific piece of equipment.
            It is sent within the Path Identification
            Message.";
          smiv2:max-access "read-write";
          smiv2:oid "1.3.6.1.2.1.10.30.9.1.2";
        }

        leaf dsx3FarEndLocationIDCode {
          type snmpv2-tc:DisplayString {
            length "0..11";
          }
          description
           "This is the Far End Location Identification code
            that describes the specific location of the
            equipment.  It is sent within the Path
            Identification Message.";
          smiv2:max-access "read-write";
          smiv2:oid "1.3.6.1.2.1.10.30.9.1.3";
        }

        leaf dsx3FarEndFrameIDCode {
          type snmpv2-tc:DisplayString {
            length "0..10";
          }
          description
           "This is the Far End Frame Identification code
            that identifies where the equipment is located
            within a building at a given location.  It is sent
            within the Path Identification Message.";
          smiv2:max-access "read-write";
          smiv2:oid "1.3.6.1.2.1.10.30.9.1.4";
        }

        leaf dsx3FarEndUnitCode {
          type snmpv2-tc:DisplayString {
            length "0..6";
          }
          description
           "This is the Far End code that identifies the
            equipment location within a bay.  It is sent
            within the Path Identification Message.";
          smiv2:max-access "read-write";
          smiv2:oid "1.3.6.1.2.1.10.30.9.1.5";
        }

        leaf dsx3FarEndFacilityIDCode {
          type snmpv2-tc:DisplayString {
            length "0..38";
          }
          description
           "This code identifies a specific Far End DS3 path.
            It is sent within the Path Identification
            Message.";
          smiv2:max-access "read-write";
          smiv2:oid "1.3.6.1.2.1.10.30.9.1.6";
        }
      }
    }

    container dsx3FarEndCurrentTable {
      description
       "The DS3 Far End Current table contains various
        statistics being collected for the current 15
        minute interval.  The statistics are collected
        from the far end block error code within the C-
        bits.";
      smiv2:oid "1.3.6.1.2.1.10.30.10";

      list dsx3FarEndCurrentEntry {
        key "dsx3FarEndCurrentIndex";
        description
         "An entry in the DS3 Far End Current table.";
        smiv2:oid "1.3.6.1.2.1.10.30.10.1";

        leaf dsx3FarEndCurrentIndex {
          type if-mib:InterfaceIndex;
          description
           "The index value which uniquely identifies the DS3
            interface to which this entry is applicable.  The
            interface identified by a particular value of this
            index is identical to the interface identified by
            the same value of dsx3LineIndex.";
          smiv2:max-access "read-only";
          smiv2:oid "1.3.6.1.2.1.10.30.10.1.1";
        }

        leaf dsx3FarEndTimeElapsed {
          type int32 {
            range "0..899";
          }
          description
           "The number of seconds that have elapsed since the
            beginning of the far end current error-measurement
            period.  If, for some reason, such as an
            adjustment in the system's time-of-day clock, the
            current interval exceeds the maximum value, the
            agent will return the maximum value.";
          smiv2:max-access "read-only";
          smiv2:oid "1.3.6.1.2.1.10.30.10.1.2";
        }

        leaf dsx3FarEndValidIntervals {
          type int32 {
            range "0..96";
          }
          description
           "The number of previous far end intervals for
            which data was collected.  The value will be
            96 unless the interface was brought online within
            the last 24 hours, in which case the value will be
            the number of complete 15 minute far end intervals
            since the interface has been online.";
          smiv2:max-access "read-only";
          smiv2:oid "1.3.6.1.2.1.10.30.10.1.3";
        }

        leaf dsx3FarEndCurrentCESs {
          type perfhist-tc:PerfCurrentCount;
          description
           "The counter associated with the number of Far Far
            End C-bit Errored Seconds.";
          smiv2:max-access "read-only";
          smiv2:oid "1.3.6.1.2.1.10.30.10.1.4";
        }

        leaf dsx3FarEndCurrentCSESs {
          type perfhist-tc:PerfCurrentCount;
          description
           "The counter associated with the number of Far End
            C-bit Severely Errored Seconds.";
          smiv2:max-access "read-only";
          smiv2:oid "1.3.6.1.2.1.10.30.10.1.5";
        }

        leaf dsx3FarEndCurrentCCVs {
          type perfhist-tc:PerfCurrentCount;
          description
           "The counter associated with the number of Far End
            C-bit Coding Violations reported via the far end
            block error count.";
          smiv2:max-access "read-only";
          smiv2:oid "1.3.6.1.2.1.10.30.10.1.6";
        }

        leaf dsx3FarEndCurrentUASs {
          type perfhist-tc:PerfCurrentCount;
          description
           "The counter associated with the number of Far End
            unavailable seconds.";
          smiv2:max-access "read-only";
          smiv2:oid "1.3.6.1.2.1.10.30.10.1.7";
        }

        leaf dsx3FarEndInvalidIntervals {
          type int32 {
            range "0..96";
          }
          description
           "The number of intervals in the range from 0 to
            dsx3FarEndValidIntervals for which no data is
            available.  This object will typically be zero
            except in cases where the data for some intervals
            are not available (e.g., in proxy situations).";
          smiv2:max-access "read-only";
          smiv2:oid "1.3.6.1.2.1.10.30.10.1.8";
        }
      }
    }

    container dsx3FarEndIntervalTable {
      description
       "The DS3 Far End Interval Table contains various
        statistics collected by each DS3 interface over
        the previous 24 hours of operation.  The past 24
        hours are broken into 96 completed 15 minute
        intervals.";
      smiv2:oid "1.3.6.1.2.1.10.30.11";

      list dsx3FarEndIntervalEntry {
        key "dsx3FarEndIntervalIndex dsx3FarEndIntervalNumber";
        description
         "An entry in the DS3 Far End Interval table.";
        smiv2:oid "1.3.6.1.2.1.10.30.11.1";

        leaf dsx3FarEndIntervalIndex {
          type if-mib:InterfaceIndex;
          description
           "The index value which uniquely identifies the DS3
            interface to which this entry is applicable.  The
            interface identified by a particular value of this
            index is identical to the interface identified by
            the same value of dsx3LineIndex.";
          smiv2:max-access "read-only";
          smiv2:oid "1.3.6.1.2.1.10.30.11.1.1";
        }

        leaf dsx3FarEndIntervalNumber {
          type int32 {
            range "1..96";
          }
          description
           "A number between 1 and 96, where 1 is the most
            recently completed 15 minute interval and 96 is
            the 15 minutes interval completed 23 hours and 45
            minutes prior to interval 1.";
          smiv2:max-access "read-only";
          smiv2:oid "1.3.6.1.2.1.10.30.11.1.2";
        }

        leaf dsx3FarEndIntervalCESs {
          type perfhist-tc:PerfIntervalCount;
          description
           "The counter associated with the number of Far End
            C-bit Errored Seconds encountered by a DS3
            interface in one of the previous 96, individual 15
            minute, intervals. In the case where the agent is
            a proxy and data is not available, return
            noSuchInstance.";
          smiv2:max-access "read-only";
          smiv2:oid "1.3.6.1.2.1.10.30.11.1.3";
        }

        leaf dsx3FarEndIntervalCSESs {
          type perfhist-tc:PerfIntervalCount;
          description
           "The counter associated with the number of Far End
            C-bit Severely Errored Seconds.";
          smiv2:max-access "read-only";
          smiv2:oid "1.3.6.1.2.1.10.30.11.1.4";
        }

        leaf dsx3FarEndIntervalCCVs {
          type perfhist-tc:PerfIntervalCount;
          description
           "The counter associated with the number of Far End
            C-bit Coding Violations reported via the far end
            block error count.";
          smiv2:max-access "read-only";
          smiv2:oid "1.3.6.1.2.1.10.30.11.1.5";
        }

        leaf dsx3FarEndIntervalUASs {
          type perfhist-tc:PerfIntervalCount;
          description
           "The counter associated with the number of Far End
            unavailable seconds.";
          smiv2:max-access "read-only";
          smiv2:oid "1.3.6.1.2.1.10.30.11.1.6";
        }

        leaf dsx3FarEndIntervalValidData {
          type boolean;
          description
           "This variable indicates if the data for this
            interval is valid.";
          smiv2:max-access "read-only";
          smiv2:oid "1.3.6.1.2.1.10.30.11.1.7";
        }
      }
    }

    container dsx3FarEndTotalTable {
      description
       "The DS3 Far End Total Table contains the
        cumulative sum of the various statistics for the
        24 hour period preceding the current interval.";
      smiv2:oid "1.3.6.1.2.1.10.30.12";

      list dsx3FarEndTotalEntry {
        key "dsx3FarEndTotalIndex";
        description
         "An entry in the DS3 Far End Total table.";
        smiv2:oid "1.3.6.1.2.1.10.30.12.1";

        leaf dsx3FarEndTotalIndex {
          type if-mib:InterfaceIndex;
          description
           "The index value which uniquely identifies the DS3
            interface to which this entry is applicable.  The
            interface identified by a particular value of this
            index is identical to the interface identified by
            the same value of dsx3LineIndex.";
          smiv2:max-access "read-only";
          smiv2:oid "1.3.6.1.2.1.10.30.12.1.1";
        }

        leaf dsx3FarEndTotalCESs {
          type perfhist-tc:PerfTotalCount;
          description
           "The counter associated with the number of Far End
            C-bit Errored Seconds encountered by a DS3
            interface in the previous 24 hour interval.
            Invalid 15 minute intervals count as 0.";
          smiv2:max-access "read-only";
          smiv2:oid "1.3.6.1.2.1.10.30.12.1.2";
        }

        leaf dsx3FarEndTotalCSESs {
          type perfhist-tc:PerfTotalCount;
          description
           "The counter associated with the number of Far End
            C-bit Severely Errored Seconds encountered by a
            DS3 interface in the previous 24 hour interval.
            Invalid 15 minute intervals count as 0.";
          smiv2:max-access "read-only";
          smiv2:oid "1.3.6.1.2.1.10.30.12.1.3";
        }

        leaf dsx3FarEndTotalCCVs {
          type perfhist-tc:PerfTotalCount;
          description
           "The counter associated with the number of Far End
            C-bit Coding Violations reported via the far end
            block error count encountered by a DS3 interface
            in the previous 24 hour interval. Invalid 15
            minute intervals count as 0.";
          smiv2:max-access "read-only";
          smiv2:oid "1.3.6.1.2.1.10.30.12.1.4";
        }

        leaf dsx3FarEndTotalUASs {
          type perfhist-tc:PerfTotalCount;
          description
           "The counter associated with the number of Far End
            unavailable seconds encountered by a DS3 interface
            in the previous 24 hour interval.  Invalid 15
            minute intervals count as 0.";
          smiv2:max-access "read-only";
          smiv2:oid "1.3.6.1.2.1.10.30.12.1.5";
        }
      }
    }

    container dsx3FracTable {
      status deprecated;
      description
       "This table is deprecated in favour of using
        ifStackTable.
        
        Implementation of this table was optional.  It was
        designed for those systems dividing a DS3/E3 into
        channels containing different data streams that
        are of local interest.
        
        The DS3/E3 fractional table identifies which
        DS3/E3 channels associated with a CSU are being
        used to support a logical interface, i.e., an
        entry in the interfaces table from the Internet-
        standard MIB.
        
        For example, consider a DS3 device with 4 high
        speed links carrying router traffic, a feed for
        voice, a feed for video, and a synchronous channel
        for a non-routed protocol.  We might describe the
        allocation of channels, in the dsx3FracTable, as
        follows:
        dsx3FracIfIndex.2. 1 = 3  dsx3FracIfIndex.2.15 = 4
        dsx3FracIfIndex.2. 2 = 3  dsx3FracIfIndex.2.16 = 6
        dsx3FracIfIndex.2. 3 = 3  dsx3FracIfIndex.2.17 = 6
        dsx3FracIfIndex.2. 4 = 3  dsx3FracIfIndex.2.18 = 6
        dsx3FracIfIndex.2. 5 = 3  dsx3FracIfIndex.2.19 = 6
        dsx3FracIfIndex.2. 6 = 3  dsx3FracIfIndex.2.20 = 6
        dsx3FracIfIndex.2. 7 = 4  dsx3FracIfIndex.2.21 = 6
        dsx3FracIfIndex.2. 8 = 4  dsx3FracIfIndex.2.22 = 6
        dsx3FracIfIndex.2. 9 = 4  dsx3FracIfIndex.2.23 = 6
        dsx3FracIfIndex.2.10 = 4  dsx3FracIfIndex.2.24 = 6
        dsx3FracIfIndex.2.11 = 4  dsx3FracIfIndex.2.25 = 6
        dsx3FracIfIndex.2.12 = 5  dsx3FracIfIndex.2.26 = 6
        dsx3FracIfIndex.2.13 = 5  dsx3FracIfIndex.2.27 = 6
        dsx3FracIfIndex.2.14 = 5  dsx3FracIfIndex.2.28 = 6
        For dsx3M23, dsx3 SYNTRAN, dsx3CbitParity, and
        dsx3ClearChannel  there are 28 legal channels,
        numbered 1 throug h 28.
        
        For e3Framed there are 16 legal channels, numbered
        1 through 16.  The channels (1..16) correspond
        directly to the equivalently numbered time-slots.";
      smiv2:oid "1.3.6.1.2.1.10.30.13";

      list dsx3FracEntry {
        key "dsx3FracIndex dsx3FracNumber";
        status deprecated;
        description
         "An entry in the DS3 Fractional table.";
        smiv2:oid "1.3.6.1.2.1.10.30.13.1";

        leaf dsx3FracIndex {
          type int32 {
            range "1..2147483647";
          }
          status deprecated;
          description
           "The index value which uniquely identifies  the
            DS3  interface  to which this entry is applicable
            The interface identified by a  particular value
            of  this  index is the same interface as
            identified by the same value  an  dsx3LineIndex
            object instance.";
          smiv2:max-access "read-only";
          smiv2:oid "1.3.6.1.2.1.10.30.13.1.1";
        }

        leaf dsx3FracNumber {
          type int32 {
            range "1..31";
          }
          status deprecated;
          description
           "The channel number for this entry.";
          smiv2:max-access "read-only";
          smiv2:oid "1.3.6.1.2.1.10.30.13.1.2";
        }

        leaf dsx3FracIfIndex {
          type int32 {
            range "1..2147483647";
          }
          status deprecated;
          description
           "An index value that uniquely identifies an
            interface.  The interface identified by a
            particular value of this index is the same
            interface as  identified by the same value an
            ifIndex object instance. If no interface is
            currently using a channel, the value should be
            zero.  If a single interface occupies more  than
            one  time slot,  that ifIndex value will be found
            in multiple time slots.";
          smiv2:max-access "read-write";
          smiv2:oid "1.3.6.1.2.1.10.30.13.1.3";
        }
      }
    }
  }

  notification dsx3LineStatusChange {
    description
     "A dsx3LineStatusChange trap is sent when the
      value of an instance of dsx3LineStatus changes. It
      can be utilized by an NMS to trigger polls.  When
      the line status change results in a lower level
      line status change (i.e. ds1), then no traps for
      the lower level are sent.";
    smiv2:oid "1.3.6.1.2.1.10.30.15.0.1";

    container object-1 {

      leaf dsx3LineIndex {
        type leafref {
          path "/DS3-MIB:DS3-MIB/DS3-MIB:dsx3ConfigTable/DS3-MIB:dsx3ConfigEntry/DS3-MIB:dsx3LineIndex";
        }
      }

      leaf dsx3LineStatus {
        type leafref {
          path "/DS3-MIB:DS3-MIB/DS3-MIB:dsx3ConfigTable/DS3-MIB:dsx3ConfigEntry/DS3-MIB:dsx3LineStatus";
        }
      }
    }

    container object-2 {

      leaf dsx3LineIndex {
        type leafref {
          path "/DS3-MIB:DS3-MIB/DS3-MIB:dsx3ConfigTable/DS3-MIB:dsx3ConfigEntry/DS3-MIB:dsx3LineIndex";
        }
      }

      leaf dsx3LineStatusLastChange {
        type leafref {
          path "/DS3-MIB:DS3-MIB/DS3-MIB:dsx3ConfigTable/DS3-MIB:dsx3ConfigEntry/DS3-MIB:dsx3LineStatusLastChange";
        }
      }
    }
  }

  smiv2:alias "ds3" {
    smiv2:oid "1.3.6.1.2.1.10.30";
  }

  smiv2:alias "ds3Conformance" {
    smiv2:oid "1.3.6.1.2.1.10.30.14";
  }

  smiv2:alias "ds3Groups" {
    smiv2:oid "1.3.6.1.2.1.10.30.14.1";
  }

  smiv2:alias "ds3Compliances" {
    smiv2:oid "1.3.6.1.2.1.10.30.14.2";
  }

  smiv2:alias "ds3Traps" {
    smiv2:oid "1.3.6.1.2.1.10.30.15";
  }

}
