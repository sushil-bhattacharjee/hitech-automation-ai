module Cisco-IOS-XE-process-cpu-oper {
  yang-version 1;
  namespace "http://cisco.com/ns/yang/Cisco-IOS-XE-process-cpu-oper";
  prefix process-cpu-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring CPU usage of processes in a Network Element.
     Copyright (c) 2016-2017, 2019 by Cisco Systems, Inc.
     All rights reserved.";

  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2017-02-07 {
    description
      "Initial revision";
    reference
      "1.0.0";
    cisco-semver:module-version "1.0.0";
  }

  grouping process-cpu-key {
    description
      "Unique process identifier";
    leaf pid {
      type uint32;
      description
        "Process-ID of the process.";
    }
    leaf name {
      type string;
      description
        "The name of the process.";
    }
  }

  grouping process-pid-cpu-usage {
    description
      "CPU usage information for a given process";
    leaf tty {
      type uint16;
      description
        "TTY bound to by the process.";
    }
    leaf total-run-time {
      type uint64;
      units "milli-seconds";
      description
        "Total Run-time of this process (mSec)";
    }
    leaf invocation-count {
      type uint32;
      description
        "Total number of invocations";
    }
    leaf avg-run-time {
      type uint64;
      units "micro-seconds";
      description
        "Average Run-time of this process (uSec)";
    }
    leaf five-seconds {
      type decimal64 {
        fraction-digits 2;
      }
      units "percent";
      description
        "Busy percentage in last 5-seconds";
    }
    leaf one-minute {
      type decimal64 {
        fraction-digits 2;
      }
      units "percent";
      description
        "Busy percentage in last one minute";
    }
    leaf five-minutes {
      type decimal64 {
        fraction-digits 2;
      }
      units "percent";
      description
        "Busy percentage in last five minutes";
    }
  }

  grouping cpu-utilization {
    description
      "Data nodes for Total CPU Utilization Statistics.";
    leaf five-seconds {
      type uint8;
      units "percent";
      description
        "Busy percentage in last 5-seconds";
    }
    leaf five-seconds-intr {
      type uint8;
      units "percent";
      description
        "Interrupt busy percentage in last 5-seconds";
    }
    leaf one-minute {
      type uint8;
      units "percent";
      description
        "Busy percentage in last one minute";
    }
    leaf five-minutes {
      type uint8;
      units "percent";
      description
        "Busy percentage in last five minutes";
    }
    container cpu-usage-processes {
      description
        "Data nodes for System wide Process CPU usage Statistics.";
      list cpu-usage-process {
        key "pid name";
        description
          "The list of software processes on the device.";
        uses process-cpu-ios-xe-oper:process-cpu-key;
        uses process-cpu-ios-xe-oper:process-pid-cpu-usage;
      }
    }
  }

  container cpu-usage {
    config false;
    description
      "CPU Utilization data";
    container cpu-utilization {
      description
        "Data nodes for Total CPU Utilization Statistics.";
      uses process-cpu-ios-xe-oper:cpu-utilization;
    }
  }
}
